FME workspace TemplateGenerator.02.fmw

Parameters:
- DestDataset_FILEGDB_11 = $(FME_MF_DIR)MNRREG_out\IDKBRUH.gdb   # File Geodatabase
- REQUESTING_USER = COMARTINMA
- REQUESTED_CLASS_LIST = TRAPLINE   # Choose a Data Class

Writers:
- FILEGDB_1: FILEGDB to $(DestDataset_FILEGDB_11)
- TEXTLINE_1: TEXTLINE to $(FME_MF_DIR)Output\success.txt
- TEXTLINE_2: TEXTLINE to $(FME_MF_DIR)Output\fail.txt

Creator
    GEOMTYPE = Geometry Object
    NUM = 1
    CREATED -> CreateAttrFromUserParam
CreateAttrFromUserParam: AttributeCreator
    ATTR_TABLE:
      SET_TO REQUESTING_USER (varchar(200)) = $(REQUESTING_USER)
      SET_TO REQUESTED_CLASS_LIST (varchar(200)) = $(REQUESTED_CLASS_LIST)
    -> FeatureReader_QueryUserPrivsTable [INITIATOR]
Note: there should be an atttribute splitter/merger
CheckMatchedRecords: TestFilter
    DEFAULT_VALUE = ResultsFromQuery
    PASSED_TEST_GROUP_OUTPUT = FIRST
    TEST_LIST = "BOOL_OP,OR,COMPOSITE_TEST,""""""1"""""",TEST_CLAUSE,TEST _matched_records ATTRIBUTE_HAS_A_VALUE """,Has Value
    Has Value -> AttributeCreator_5
    ResultsFromQuery -> SQLExecutor [INITIATOR]
AttributeCreator_5
    ATTR_TABLE = SET_TO text_line_data (varchar(200)) = LogMessage = 'Match found for user: @Value(REQUESTING_USER)'
    -> text_line (writer TEXTLINE_1)
text_line (writer TEXTLINE_1)
    attributes: text_line_data buffer, text_line_data00 buffer
Note: should it also query owner or will it always be LIO.
Note: this is prob where join table will need to be (on class_short_name)
SQLExecutor
    COMBINE_ATTRS = Result Attributes Only
    COMBINE_GEOM = Initiator Geometry Only
    DATASET = LIO_READ_WH
    EXPOSED_ATTRIBUTE_LIST = TABLE_NAME
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      SELECT table_name
      FROM all_tables
      WHERE owner = 'LIO'
      and table_name like '%@Value(REQUESTED_CLASS_LIST)%'



      --SELECT table_name
      --FROM all_tables
      --WHERE table_name like '@Value(REQUESTED_CLASS_LIST)'

      --SELECT table_name
      --FROM all_tables
      --WHERE table_name LIKE '%$(REQUESTED_CLASS_LIST)%'


      --SELECT table_name
      --FROM all_tables
      --WHERE table_name = 'LIO.AIRPORT_OFFICIAL_FT'



          --AND table_name LIKE '%$(REQUESTED_CLASS_LIST)%'
       --AND table_name LIKE '%EVAL%' --AIRPORT AIRPTOFF
        --AND table_name LIKE '%' || @Value(REQUESTED_CLASS_LIST) || '%'


      --SELECT table_name
      --FROM all_tables
      --WHERE table_name LIKE '%$(REQUESTED_CLASS_LIST)%'
    RESULT -> append_owner_prefix_LIO
    RESULT -> SQLExecutor_4 [INITIATOR]
append_owner_prefix_LIO: AttributeManager
    ATTR_TABLE = SET_TO TABLE_NAME (buffer) = LIO.@Value(TABLE_NAME)
    -> FeatureReader_2 [INITIATOR]
    -> SQLExecutor_3 [INITIATOR]
SQLExecutor_3
    COMBINE_ATTRS = Result Attributes Only
    COMBINE_GEOM = Initiator Geometry Only
    DATASET = LIO_READ_WH
    EXPOSED_ATTRIBUTE_LIST = TABLE_NAME
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      SELECT * FROM @Value(TABLE_NAME)

      --and @Value like '%@Value(TABLE_NAME)%'
FeatureReader_2
    ATTRS_TO_EXPOSE = fme_feature_type
    ATTR_ACCUM_MODE = Only Use Result
    COMBINE_GEOM = Use Result
    DATASET = LIO_READ_WH
    FEATURETYPES = @Value(TABLE_NAME)
    FORMAT = ORACLE_SPATIAL
    INTERACT = NONE
    MAX_FEATURES = 100
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = LIO_READ_WH
    ORACLE_SPATIAL_ORACLE_SPATIAL_EXPOSE_FORMAT_ATTRS = fme_dataset,char(50) fme_feature_type,char(50) oracle_srid,char(50) oracle_type,char(50)
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = YES
    ORACLE_SPATIAL_USE_SEARCH_ENVELOPE = NO
    ORACLE_SPATIAL_USE_UNIFIED_DATE_ATTRS = YES
    ORDER_RESULTS = No
    OUTPUT_FEATURES_DISPLAY = Schema and Data Features
Note: maybe: need to include OWNER type in the query
SQLExecutor_4
    COMBINE_ATTRS = Result Attributes Only
    COMBINE_GEOM = Initiator Geometry Only
    DATASET = LIO_READ_WH
    EXPOSED_ATTRIBUTE_LIST = OWNER,TABLE_NAME,COLUMN_NAME,DATA_TYPE,COLUMN_ID
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      SELECT OWNER, TABLE_NAME, COLUMN_NAME, DATA_TYPE, COLUMN_ID from all_tab_columns
      where TABLE_NAME = '@Value(TABLE_NAME)'
ParameterFetcher
AttributeExploder
    ATTR_NAME_LABEL = _attr_name
    ATTR_VALUE_LABEL = _attr_value
    CASE = No
    EXPLODING_TYPE = List
    KEEP_ATTRIBUTES = Yes
    KEEP_GEOMETRY = No
    LIST_NAME = _attr_list

Bookmark: Verify User Exists In Y_USER_PRIVS Table
Note: Checks for user name with SQL "where" clause. better on memory and speed versus loading it all in then comparing. / _matched_records indicates number of features returned who's user_name matches the requested user's. this attribute is used next in the Tester
FeatureReader_QueryUserPrivsTable
    ATTRIBUTES = LIO.Y_USER_PRIVILEGES,"USER_NAME,CLASS_SHORT_NAME,SUSPENDED,CAN_EDIT,CAN_CHECK_IN,ADMINISTRATOR,FULL_REPLACE,AOR_RESTRICTION,EFFECTIVE_DATETIME"
    ATTR_ACCUM_MODE = Only Use Result
    COMBINE_GEOM = Use Result
    DATASET = LIO_READ_WH
    FEATURETYPES = LIO.Y_USER_PRIVILEGES
    FORMAT = ORACLE_NONSPATIAL
    ORACLE_NONSPATIAL_CHUNK_SIZE = 200
    ORACLE_NONSPATIAL_CREATE_FEATURE_TABLES_FROM_DATA = Yes
    ORACLE_NONSPATIAL_NAMED_CONNECTION = LIO_READ_WH
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    ORDER_RESULTS = No
    OUTPUT_FEATURES_DISPLAY = Schema and Data Features
    WHERE:
      USER_NAME = '@Value(REQUESTING_USER)'
      AND SUSPENDED = 'No' --assuming matt's workspace validates this
      --before getting here but you never know
      AND "CLASS_SHORT_NAME" = '@Value(REQUESTED_CLASS_LIST)'
      --^also don't know if necessary but check if they supposed to access
      -- the requested database
    LIO.Y_USER_PRIVILEGES -> AttributeManager_CombineOutput
    INITIATOR -> AttributeManager_CombineOutput
AttributeManager_CombineOutput
    ATTR_TABLE:
      REMOVE REQUESTING_USER (varchar(200))
      REMOVE REQUESTED_CLASS_LIST (varchar(200))
      RENAME_SET_VALUE CLASS_SHORT_NAME > REQUESTED_CLASS_LIST (varchar(8))
      REMOVE SUSPENDED (varchar(3))
      REMOVE CAN_EDIT (varchar(3))
      REMOVE CAN_CHECK_IN (varchar(3))
      REMOVE ADMINISTRATOR (varchar(3))
      REMOVE FULL_REPLACE (varchar(3))
      REMOVE AOR_RESTRICTION (varchar(1000))
      REMOVE EFFECTIVE_DATETIME (datetime)
    -> TesterUserFound
TesterUserFound
    BOOL_OP = OR
    TEST_CLAUSE = TEST @Value(_matched_records) != 0
    TEST_MODE = TEST
    PASSED -> CheckMatchedRecords
    FAILED -> AttributeCreator_4

Bookmark: NeedToMakeErrorHTML
AttributeCreator_4
    ATTR_TABLE = SET_TO text_line_data (varchar(200)) = LogMessage = 'No match found for user: @Value(REQUESTING_USER)'
    -> text_line (writer TEXTLINE_2)
text_line (writer TEXTLINE_2)
    attributes: text_line_data buffer, text_line_data00 buffer

Bookmark: This works to dynamically write queried geo data to a file gdb
Creator_7
    GEOMTYPE = Geometry Object
    NUM = 1
    CREATED -> RenameTableToQuery_AttrMngr
RenameTableToQuery_AttrMngr: AttributeManager
    ATTR_TABLE:
      RENAME_SET_VALUE table_name > table_name_old (uint64) = LIO.TRAPLINE_AREA_FT
      SET_TO table_name (buffer) = LIO.TRAPPER_CABIN_FT
    USER_EXPOSED_ATTRIBUTES = fme_feature_type
    -> FeatureReader_7 [INITIATOR]
FeatureReader_7
    ATTRS_TO_EXPOSE = fme_feature_type
    ATTR_ACCUM_MODE = Only Use Result
    COMBINE_GEOM = Use Result
    DATASET = LIO_READ_WH
    FEATURETYPES = @Value(table_name)
    FORMAT = ORACLE_SPATIAL
    INTERACT = NONE
    MAX_FEATURES = 100
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = LIO_READ_WH
    ORACLE_SPATIAL_ORACLE_SPATIAL_EXPOSE_FORMAT_ATTRS = fme_dataset,char(50) fme_feature_type,char(50) oracle_srid,char(50) oracle_type,char(50)
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = YES
    ORACLE_SPATIAL_USE_SEARCH_ENVELOPE = NO
    ORACLE_SPATIAL_USE_UNIFIED_DATE_ATTRS = YES
    ORDER_RESULTS = No
    OUTPUT_FEATURES_DISPLAY = Schema and Data Features
    <OTHER> -> SchemaScanner_LIO
Note: - need to get actual data types from db / - need to see if it works w multiple tables
SchemaScanner_LIO
    CASE = No
    EMPTY_ATTR_HANDLING = IGNORE
    HOLD = Yes
    NUMERIC_ALLOW_LEADING_ZEROES = Yes
    SCHEMA_NAME_ATTR = fme_feature_type_name
    UNBOUNDED_NUMBERS = Yes
    UNBOUNDED_STRINGS = No
    -> FeatureClass1000100 (writer FILEGDB_1)
    <SCHEMA> -> FeatureClass1000100 (writer FILEGDB_1)
    <SCHEMA> -> FeatureClass100010000 (writer FILEGDB_1)
Note: this is the one that is only given schema as input and doesn't print/write
FeatureClass100010000 (writer FILEGDB_1)
Note: need a dynamic style for the file location?
FeatureClass1000100 (writer FILEGDB_1)
