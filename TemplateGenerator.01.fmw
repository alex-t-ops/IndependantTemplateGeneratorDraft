FME workspace TemplateGenerator.01.fmw

Parameters:
- REQUESTING_USER = COMARTINMA
- REQUESTED_CLASS_LIST = TRAPLINE   # Choose a Data Class
- FILE_FORMAT = .gdb   # File Geodatabase,.gdb%GeoPackage,.gpkg File Geodatabase or GeoPackage
- INCLUDE_RELATIONSHIPS = NO   # INCLUDE_RELATIONSHIPS Yes/No
- INCLUDE_DOMAINS = NO   # INCLUDE_DOMAINS Yes/No 2
- POPULATE_DATA = NO   # POPULATE_DATA Yes/No
- PROJECTION = EPSG4326   # Select a Coordinate System (PROJECTION)
- DATA_BACKUP = NO   # DATA_BACKUP Yes/No
- REQUESTED_CLASS_LIST-bad = LIO.AIRPORT_OFFICIAL_FT   # LIO.AIRPORT_OFFICIAL_FT REQUESTED_CLASS_LIST
- DestDataset_FILEGDB = $(FME_MF_DIR)Output\test_empty_template.gdb   # File Geodatabase
- DestDataset_GEODATABASE_FILE = $(FME_MF_DIR)Output\test_empty_template.gdb   # File Geodatabase
- DestDataset_FILEGDB_10 = $(FME_MF_DIR)Output\test_empty_template.gdb   # File Geodatabase
- SourceDataset_ORACLE_SPATIAL = LIO_READ_WH   # Connection
- DestDataset_FILEGDB_4 = $(FME_MF_DIR)Output\Output.gdb   # File Geodatabase
- SourceDataset_FILEGDB = $(FME_MF_DIR)Output\TRAPLINE_AREA_FT.gdb   # File Geodatabase
- DestDataset_FILEGDB_12 = $(FME_MF_DIR)MNRREG_out\IDKBRUH.gdb   # File Geodatabase
- SourceDataset_XML = C:\Users\TuAl\OneDrive - Government of Ontario\Documents\GEO-Validator\Test\Data\domains - Copy.xml   # Source XML File(s)
- DestDataset_FILEGDB_9 = C:\Users\TuAl\OneDrive - Government of Ontario\Documents\GEO-Validator\Test\Output\MNRREG_out\IDKBRUH.gdb   # File Geodatabase
- SourceDataset_TEXTLINE = $(FME_MF_DIR)WORKSPACE\export_without_metadata.xml   # Source Text File(s)
- SourceDataset_ORACLE_SPATIAL_3 = LIO_READ_WH   # Connection
- DestDataset_ORACLE_SPATIAL = LIO_READ_WH   # Connection
- DestDataset_FILEGDB_11 = $(FME_MF_DIR)MNRREG_out\IDKBRUH.gdb   # File Geodatabase

Readers:
- ORACLE_SPATIAL_1: ORACLE_SPATIAL from $(SourceDataset_ORACLE_SPATIAL)
- FILEGDB_4: FILEGDB from $(SourceDataset_FILEGDB)
- XML_1: XML from $(SourceDataset_XML)
- TEXTLINE_3: TEXTLINE from $(SourceDataset_TEXTLINE)
- ORACLE_SPATIAL_2: ORACLE_SPATIAL from $(SourceDataset_ORACLE_SPATIAL_3)

Writers:
- TEXTLINE_1: TEXTLINE to $(FME_MF_DIR)Output\success.txt
- TEXTLINE_2: TEXTLINE to $(FME_MF_DIR)Output\fail.txt
- FILEGDB_1: FILEGDB to $(DestDataset_FILEGDB)
- GEODATABASE_FILE_1: GEODATABASE_FILE to $(DestDataset_GEODATABASE_FILE)
- FILEGDB_2: FILEGDB to $(DestDataset_FILEGDB_10)
- FILEGDB_3: FILEGDB to $(DestDataset_FILEGDB_4)
- FILEGDB_5: FILEGDB to $(FME_MF_DIR)MNRREG_out\IDKBRUH.gdb
- FILEGDB_6: FILEGDB to $(DestDataset_FILEGDB_12)
- FILEGDB_7: FILEGDB to $(DestDataset_FILEGDB_9)
- ORACLE_SPATIAL_3: ORACLE_SPATIAL to $(DestDataset_ORACLE_SPATIAL)
- FILEGDB_8: FILEGDB to $(DestDataset_FILEGDB_11)

Creator_4
    GEOMTYPE = Geometry Object
    NUM = 1
    CREATED -> FeatureReader_6 [INITIATOR]
FeatureReader_6
    ATTRIBUTES = LIO.TRAPLINE_AREA_FT,"OGF_ID,TRAPLINE_AREA_NUMBER,TRAPLINE_TYPE_CODE,TRAPLINE_STATUS_CODE,STATUS_COMMENTS_DESCR,TRAPPER_LICENSE_CODE,STRUCTURES_NUM,LOCATION_ACCURACY,LOCATION_DESCR,GEOG_UNIT_DESCR,VERIFICATION_STATUS_FLG,VERIFICATION_STATUS_DATE,BUSINESS_EFF_DATE_FLG,BUSINESS_EFFECTIVE_DATE,SYSTEM_CALCULATED_AREA,SYSTEM_CALCULATED_LENGTH,USER_CALCULATED_METRIC,GENERAL_COMMENTS,GEOMETRY_UPDATE_DATETIME,EFFECTIVE_DATETIME,SYSTEM_DATETIME,OBJECTID,SE_ANNO_CAD_DATA"
    ATTR_ACCUM_MODE = Only Use Result
    COMBINE_GEOM = Use Result
    DATASET = LIO_READ_2
    FEATURETYPES = LIO.TRAPLINE_AREA_FT
    FORMAT = ORACLE_NONSPATIAL
    ORACLE_NONSPATIAL_CHUNK_SIZE = 200
    ORACLE_NONSPATIAL_CREATE_FEATURE_TABLES_FROM_DATA = Yes
    ORACLE_NONSPATIAL_NAMED_CONNECTION = LIO_READ_2
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    ORDER_RESULTS = No
    OUTPUT_FEATURES_DISPLAY = Schema and Data Features
    LIO.TRAPLINE_AREA_FT -> AttributeExposer_6
AttributeExposer_6
    ATTR_TABLE = fme_feature_type,
    -> FeatureWriter_5 [Aggregate]
FeatureWriter_5
    DATASET = @Value(fme_feature_type)
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = NO
    FILEGDB_WRITE_UNZONED_UTC = No
    FORMAT = FILEGDB
    GROUP_BY = fme_feature_type
    TOTAL_FEATURES_WRITTEN_ATTR = _total_features_written
    Aggregate -> CSV (writer FILEGDB_6)
CSV (writer FILEGDB_6)
    attributes: OGF_ID text(20), TRAPLINE_AREA_NUMBER text(12), TRAPLINE_TYPE_CODE text(30), TRAPLINE_STATUS_CODE text(10), STATUS_COMMENTS_DESCR text(2000), TRAPPER_LICENSE_CODE text(35), STRUCTURES_NUM smallint, LOCATION_ACCURACY text(25), LOCATION_DESCR text(2000), GEOG_UNIT_DESCR text(2000), VERIFICATION_STATUS_FLG text(10), VERIFICATION_STATUS_DATE date, BUSINESS_EFF_DATE_FLG text(10), BUSINESS_EFFECTIVE_DATE date, SYSTEM_CALCULATED_AREA double, SYSTEM_CALCULATED_LENGTH double, USER_CALCULATED_METRIC double, GENERAL_COMMENTS text(2000), GEOMETRY_UPDATE_DATETIME date, EFFECTIVE_DATETIME date, SYSTEM_DATETIME date, OBJECTID double, SE_ANNO_CAD_DATA blob
ParameterFetcher
Creator
    GEOMTYPE = Geometry Object
    NUM = 1
    CREATED -> CreateAttrFromUserParam
CreateAttrFromUserParam: AttributeCreator
    ATTR_TABLE:
      SET_TO REQUESTING_USER (varchar(200)) = $(REQUESTING_USER)
      SET_TO REQUESTED_CLASS_LIST (varchar(200)) = $(REQUESTED_CLASS_LIST)
    -> FeatureReader_QueryUserPrivsTable [INITIATOR]
Note: there should be an atttribute splitter/merger
CheckMatchedRecords: TestFilter
    DEFAULT_VALUE = ResultsFromQuery
    PASSED_TEST_GROUP_OUTPUT = FIRST
    TEST_LIST = "BOOL_OP,OR,COMPOSITE_TEST,""""""1"""""",TEST_CLAUSE,TEST _matched_records ATTRIBUTE_HAS_A_VALUE """,Has Value
    Has Value -> AttributeCreator_5
    ResultsFromQuery -> SQLExecutor [INITIATOR]
AttributeCreator_5
    ATTR_TABLE = SET_TO text_line_data (varchar(200)) = LogMessage = 'Match found for user: @Value(REQUESTING_USER)'
    -> text_line (writer TEXTLINE_1)
text_line (writer TEXTLINE_1)
    attributes: text_line_data buffer, text_line_data00 buffer
Note: should it also query owner or will it always be LIO.
Note: this is prob where join table will need to be (on class_short_name)
SQLExecutor
    COMBINE_ATTRS = Result Attributes Only
    COMBINE_GEOM = Initiator Geometry Only
    DATASET = LIO_READ_WH
    EXPOSED_ATTRIBUTE_LIST = TABLE_NAME
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      SELECT table_name
      FROM all_tables
      WHERE owner = 'LIO'
      and table_name like '%@Value(REQUESTED_CLASS_LIST)%'



      --SELECT table_name
      --FROM all_tables
      --WHERE table_name like '@Value(REQUESTED_CLASS_LIST)'

      --SELECT table_name
      --FROM all_tables
      --WHERE table_name LIKE '%$(REQUESTED_CLASS_LIST)%'


      --SELECT table_name
      --FROM all_tables
      --WHERE table_name = 'LIO.AIRPORT_OFFICIAL_FT'



          --AND table_name LIKE '%$(REQUESTED_CLASS_LIST)%'
       --AND table_name LIKE '%EVAL%' --AIRPORT AIRPTOFF
        --AND table_name LIKE '%' || @Value(REQUESTED_CLASS_LIST) || '%'


      --SELECT table_name
      --FROM all_tables
      --WHERE table_name LIKE '%$(REQUESTED_CLASS_LIST)%'
    RESULT -> append_owner_prefix_LIO
    RESULT -> SQLExecutor_4 [INITIATOR]
append_owner_prefix_LIO: AttributeManager
    ATTR_TABLE = SET_TO TABLE_NAME (buffer) = LIO.@Value(TABLE_NAME)
    -> FeatureReader_2 [INITIATOR]
    -> SQLExecutor_3 [INITIATOR]
SQLExecutor_3
    COMBINE_ATTRS = Result Attributes Only
    COMBINE_GEOM = Initiator Geometry Only
    DATASET = LIO_READ_WH
    EXPOSED_ATTRIBUTE_LIST = TABLE_NAME
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      SELECT * FROM @Value(TABLE_NAME)

      --and @Value like '%@Value(TABLE_NAME)%'
FeatureReader_2
    ATTRS_TO_EXPOSE = fme_feature_type
    ATTR_ACCUM_MODE = Only Use Result
    COMBINE_GEOM = Use Result
    DATASET = LIO_READ_WH
    FEATURETYPES = @Value(TABLE_NAME)
    FORMAT = ORACLE_SPATIAL
    INTERACT = NONE
    MAX_FEATURES = 100
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = LIO_READ_WH
    ORACLE_SPATIAL_ORACLE_SPATIAL_EXPOSE_FORMAT_ATTRS = fme_dataset,char(50) fme_feature_type,char(50) oracle_srid,char(50) oracle_type,char(50)
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = YES
    ORACLE_SPATIAL_USE_SEARCH_ENVELOPE = NO
    ORACLE_SPATIAL_USE_UNIFIED_DATE_ATTRS = YES
    ORDER_RESULTS = No
    OUTPUT_FEATURES_DISPLAY = Schema and Data Features
    <OTHER> -> AttributeFilter
    <OTHER> -> ListBuilder
    <OTHER> -> Aggregator
    <OTHER> -> AttributeExposer
    <OTHER> -> PythonCaller
    <OTHER> -> SchemaScanner
    <OTHER> -> FeatureClass1 (writer FILEGDB_2)
    <OTHER> -> FeatureWriter_2 [Aggregate]
    INITIATOR -> AttributeFilter
FeatureWriter_2
    DATASET = $(FME_MF_DIR_ENCODED)Output\Output.gdb
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = YES
    FILEGDB_WRITE_UNZONED_UTC = No
    FORMAT = FILEGDB
    GROUP_BY = fme_feature_type
    TOTAL_FEATURES_WRITTEN_ATTR = _total_features_written
    Aggregate -> FeatureClass100 (writer FILEGDB_3)
    SUMMARY -> FeatureClass100 (writer FILEGDB_3)
FeatureClass100 (writer FILEGDB_3)
    attributes: _dataset text(2048), _total_features_written text(20)
Aggregator
    ACCUM_ATTRS_NAME = Drop Incoming Attributes
    AGGREGATE_TYPE = Homogeneous Collection (If Possible)
    GROUP_BY = fme_feature_type
    LIST_NAME = rows
    MODE = Geometry - Assemble One Level
    SEP = ,
PythonCaller
    GROUP_BY = fme_feature_type
    PYTHONSOURCE:
      import fme
      import fmeobjects


      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """
              self.pyoutput(feature)

          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
ListBuilder
    GROUP_BY = fme_feature_type
    LIST_NAME = _list
    -> ListExploder
    -> AttributeExploder_2
AttributeExploder_2
    ATTR_NAME_LABEL = _attr_name
    ATTR_VALUE_LABEL = _attr_value
    CASE = No
    EXPLODING_TYPE = Features
    KEEP_ATTRIBUTES = No
    KEEP_GEOMETRY = No
    -> AttributeFilter_2
AttributeFilter_2
    ATTR_VALUES = <Empty>,<Missing>,<Null>,<Unfiltered>
ListExploder
    ATTR_ACCUM_MODE = Merge List Attributes
    ATTR_CONFLICT_RES = Use List Attribute Values
    INDEX_ATTR = _element_index
    LIST_ATTR = _list{}
    ELEMENTS -> FeatureTypeExtractor
FeatureTypeExtractor
    DEST_ATTR = _feature_type
FeatureClass1 (writer FILEGDB_2)
SchemaScanner
    CASE = No
    EMPTY_ATTR_HANDLING = IGNORE
    GROUP_BY = fme_feature_type
    HOLD = Yes
    NUMERIC_ALLOW_LEADING_ZEROES = Yes
    SCHEMA_NAME_ATTR = fme_feature_type_name
    UNBOUNDED_NUMBERS = Yes
    UNBOUNDED_STRINGS = No
    <SCHEMA> -> FeatureClass1 (writer GEODATABASE_FILE_1)
    <SCHEMA> -> ListExploder_3
    <SCHEMA> -> AttributeExploder_6
    <SCHEMA> -> ListConcatenator_2
    <SCHEMA> -> ListExploder_2
ListExploder_3
    ATTR_ACCUM_MODE = Merge List Attributes
    ATTR_CONFLICT_RES = Use List Attribute Values
    INDEX_ATTR = _element_index
    LIST_ATTR = attribute{}
    ELEMENTS -> AttributeCreator_8
AttributeCreator_8
    ATTR_TABLE = SET_TO @Value(name) (buffer) = @Value(name)
    -> AttributeExposer_2
AttributeExposer_2
    ATTR_TABLE = @Value(name),buffer
ListConcatenator_2
    DROP_EMPTY_PARTS = No
    LIST_ATTR = attribute{}.name
    SEP = ,
    VAL_ATTR = _concatenated
    -> SubstringExtractor
Note: woul dhave to calculate the length of each, beforehand?
SubstringExtractor
    END = -1
    RESULT_ATTR = _substring
    START = 0
FeatureClass1 (writer GEODATABASE_FILE_1)
    attributes: fme_feature_type_name char(2048)
AttributeExploder_6
    ATTR_NAME_LABEL = _attr_name
    ATTR_VALUE_LABEL = _attr_value
    CASE = No
    EXPLODING_TYPE = Features
    KEEP_ATTRIBUTES = No
    KEEP_GEOMETRY = No
    -> AttributeCreator_9
    -> AttributeManager_2
    -> TestFilter_3
AttributeCreator_9
AttributeManager_2
TestFilter_3
    DEFAULT_VALUE = <unfiltered>
    PASSED_TEST_GROUP_OUTPUT = FIRST
    TEST_LIST = "BOOL_OP,OR,COMPOSITE_TEST,""""""1"""""",TEST_CLAUSE,CASE_INSENSITIVE_TEST @Value(_attr_name) CONTAINS fme_data_type",data_type,"BOOL_OP,OR,COMPOSITE_TEST,""""""1"""""",TEST_CLAUSE,CASE_INSENSITIVE_TEST @Value(_attr_name) CONTAINS name",column_name
AttributeExposer
AttributeFilter
    ATTR_NAME = fme_feature_type
    ATTR_VALUES = <Empty>,<Missing>,<Null>,<Unfiltered>,LIO.TRAPLINE_AREA_FT,LIO.TRAPLINE_AREA_STATUS,LIO.TRAPLINE_TYPE
Note: maybe: need to include OWNER type in the query
SQLExecutor_4
    COMBINE_ATTRS = Result Attributes Only
    COMBINE_GEOM = Initiator Geometry Only
    DATASET = LIO_READ_WH
    EXPOSED_ATTRIBUTE_LIST = OWNER,TABLE_NAME,COLUMN_NAME,DATA_TYPE,COLUMN_ID
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      SELECT OWNER, TABLE_NAME, COLUMN_NAME, DATA_TYPE, COLUMN_ID from all_tab_columns
      where TABLE_NAME = '@Value(TABLE_NAME)'
    RESULT -> AttributeManager_7
    RESULT -> AttributeCreator_10
    RESULT -> AttributeExploder_7
    RESULT -> StringConcatenator
    RESULT -> AttributeManager_6
    RESULT -> FeatureClass1 (writer FILEGDB_3)
AttributeManager_6
    ATTR_TABLE = RENAME_SET_VALUE TABLE_NAME > fme_feature_type (varchar(128))
    -> Aggregator_3
    -> ListBuilder_2
ListBuilder_2
    GROUP_BY = fme_feature_type
    LIST_ATTRS_TO_INCLUDE = COLUMN_ID COLUMN_NAME DATA_TYPE
    LIST_NAME = _list
    -> ListConcatenator_3
    -> FeatureWriter [Aggregate]
    -> ListExploder_5
ListConcatenator_3
    DROP_EMPTY_PARTS = No
    LIST_ATTR = _list{}.COLUMN_NAME
    SEP = ,
    VAL_ATTR = _concatenated
    -> ListExploder_4
    -> SubstringExtractor_2
SubstringExtractor_2 [off]
    END = @StringLength(@Value(_list{@CurrentAttribute()}.COLUMN_NAME))
    RESULT_ATTR = _substring
    SRC_STRING = @Value(_concatenated)
    START = @StringLength(@Value(_list{@CurrentAttribute(-1)}.COLUMN_NAME))
ListExploder_4
    ATTR_ACCUM_MODE = Merge List Attributes
    ATTR_CONFLICT_RES = Use List Attribute Values
    INDEX_ATTR = _element_index
    LIST_ATTR = _list{}
FeatureWriter
    DATASET = $(FME_MF_DIR_ENCODED)Output\NULL.gdb
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = YES
    FILEGDB_WRITE_UNZONED_UTC = No
    FORMAT = FILEGDB
    GROUP_BY = fme_feature_type
    TOTAL_FEATURES_WRITTEN_ATTR = _total_features_written
ListExploder_5
    ATTR_ACCUM_MODE = Merge List Attributes
    ATTR_CONFLICT_RES = Use List Attribute Values
    INDEX_ATTR = _element_index
    LIST_ATTR = _list{}
Aggregator_3
    ACCUM_ATTRS_NAME = Merge Incoming Attributes
    CONCAT_ATTRS = COLUMN_ID COLUMN_NAME DATA_TYPE
    GROUP_BY = fme_feature_type
    MODE = Attributes Only
    SEP = ,
    AGGREGATE -> AttributeManager_8
AttributeManager_8
    ATTR_TABLE = RENAME_SET_VALUE fme_feature_type (varchar(128))
    -> AttributeFilter_3
AttributeFilter_3
    ATTR_NAME = fme_feature_type
    ATTR_VALUES = <Empty>,<Missing>,<Null>,<Unfiltered>
AttributeCreator_10
    ATTR_TABLE = SET_TO @Value(TABLE_NAME) (varchar(128)) = @Value(DATA_TYPE)
FeatureClass1 (writer FILEGDB_3)
    attributes: OWNER text(128), TABLE_NAME text(128), COLUMN_NAME text(128), DATA_TYPE text(128), COLUMN_ID double
AttributeExploder_7
    ATTR_NAME_LABEL = _attr_name
    ATTR_VALUE_LABEL = _attr_value
    CASE = No
    EXPLODING_TYPE = Features
    KEEP_ATTRIBUTES = No
    KEEP_GEOMETRY = No
StringConcatenator
    ACTION = Create New Attribute
    PARM_LINE = @Value(OWNER),@Value(TABLE_NAME),@Value(COLUMN_NAME),@Value(DATA_TYPE),@Value(COLUMN_ID)
    VAL_ATTR = full_columns
AttributeManager_7
QueryRequestedClassListFromLIO: FeatureReader
    ATTRIBUTES = LIO.ABORIGINAL_ASSERTION_AREA_FT,"OGF_ID,FEATURE_SOURCE_CLASS_NAME,ASSERTION_TYPE,ASSERTION_SUBTYPE,COMMUNITY_SUBM_ASSERT_STATUS,CREDIBLE_CLAIM_STRENGTH,COMMUNITY_CATEGORY,COMMUNITY_NAME,COMMUNITY_TRAD_NAME,COMMUNITY_COO_NAME,ASSERTION_NUMBER,LOCATION_DESCR,VERIFICATION_STATUS_FLG,VERIFICATION_STATUS_DATE,ASSERTION_RECORD_GUID,COMMUNITY_RECORD_GUID,FEATURE_RECORD_GUID,GEOMETRY_UPDATE_DATETIME,EFFECTIVE_DATETIME,SYSTEM_DATETIME,OBJECTID,SE_ANNO_CAD_DATA",LIO.ABORIGINAL_ASSERTION_LINE_FT,"OGF_ID,ABORIGINAL_ASSERTION_ID,PUBLISH_TO_VIEW_IND,SENSITIVITY_CLASS,SENSITIVITY_RATIONALE,LOCATION_DESCR,VERIFICATION_STATUS_FLG,VERIFICATION_STATUS_DATE,ASSERTION_RECORD_GUID,FEATURE_RECORD_GUID,GEOMETRY_UPDATE_DATETIME,EFFECTIVE_DATETIME,SYSTEM_DATETIME,SE_ANNO_CAD_DATA,OBJECTID",LIO.ABORIGINAL_ASSERTION_POINT_FT,"OGF_ID,ABORIGINAL_ASSERTION_ID,PUBLISH_TO_VIEW_IND,SENSITIVITY_CLASS,SENSITIVITY_RATIONALE,LOCATION_DESCR,VERIFICATION_STATUS_FLG,VERIFICATION_STATUS_DATE,ASSERTION_RECORD_GUID,FEATURE_RECORD_GUID,GEOMETRY_UPDATE_DATETIME,EFFECTIVE_DATETIME,SYSTEM_DATETIME,SE_ANNO_CAD_DATA,OBJECTID",LIO.ABORIGINAL_ASSERTION_POLY_FT,"OGF_ID,ABORIGINAL_ASSERTION_ID,PUBLISH_TO_VIEW_IND,SENSITIVITY_CLASS,SENSITIVITY_RATIONALE,LOCATION_DESCR,VERIFICATION_STATUS_FLG,VERIFICATION_STATUS_DATE,ASSERTION_RECORD_GUID,FEATURE_RECORD_GUID,GEOMETRY_UPDATE_DATETIME,EFFECTIVE_DATETIME,SYSTEM_DATETIME,SE_ANNO_CAD_DATA,OBJECTID",LIO.ADDITIONAL_NATURAL_AREA_FT,"OGF_ID,NATURAL_AREA_IDENT,NATURAL_AREA_NAME,AREA_TYPE,AREA_SIGNIFICANCE,ESTIMATED_AREA_HA,SENSITIVITY_CLASS,SENSITIVITY_DATE,SENSITIVITY_RATIONALE,SENS_RATIONALE_OTHER_DESCR,LOCATION_ACCURACY,VERSION_AUTHOR_NAME,VERSION_DATE,GEOMETRY_UPDATE_DATETIME,EFFECTIVE_DATETIME,SYSTEM_DATETIME,SE_ANNO_CAD_DATA,OBJECTID",LIO.AGGSITE_AUTHORIZED_PART_SUR_FT,"OGF_ID,ALPS_ID,PARTIAL_SURRENDER_IND,CURRENT_STATUS,CLIENT_NAME,OPERATION_TYPE,AUTH_TYPE_DESCR,UNLIMITED_TONNAGE_IND,MAX_TONNAGE,WATER_STATUS,LICENCED_AREA,LOCATION_NAME,LOCATION_ACCURACY,SOURCE_DETAIL,EFFECTIVE_DATETIME,SYSTEM_DATETIME,SE_ANNO_CAD_DATA,OBJECTID",LIO.AGG_CATEGORY_14_SITE_FT,"OGF_ID,FOREST_ROAD_AGG_OPERATOR,START_OF_OPERATION_DATE,GEOMETRY_UPDATE_DATETIME,EFFECTIVE_DATETIME,SYSTEM_DATETIME,OBJECTID,SE_ANNO_CAD_DATA",LIO.AGRICULTURAL_LAND_INFO_FT,"OGF_ID,GIS_ID,AGRICULTURAL_USE_TYPE,GEOMETRY_UPDATE_DATETIME,EFFECTIVE_DATETIME,SYSTEM_DATETIME,OBJECTID,SE_ANNO_CAD_DATA",LIO.AIRPORT_OFFICIAL_FT,"OGF_ID,AIRPORT_TYPE,STATUS,NAME,OWNER,AIRPORT_IDENT,LATITUDE,LONGITUDE,ELEVATION,NUMBER_OF_PAVED_RUNWAYS,NUMBER_OF_UNPAVED_RUNWAYS,LGTH_LONGEST_DAYTIME_RUNWAY,LGTH_LONGEST_NIGHTTIME_RUNWAY,CONTROL_TOWER_IND,INSTRUMENT_FLIGHT_RULES_IND,VISUAL_FLIGHT_RULES_IND,AIRPORT_LIGHTING,AIRPORT_AREA_HA,COMMENTS,SOURCE_DETAIL,LOCATION_ACCURACY,GEOMETRY_UPDATE_DATETIME,EFFECTIVE_DATETIME,SYSTEM_DATETIME,SE_ANNO_CAD_DATA,OBJECTID",LIO.AIRPORT_OTHER_FT,"OGF_ID,AIRPORT_TYPE,STATUS,NAME,OWNER,AIRPORT_IDENT,LATITUDE,LONGITUDE,ELEVATION,NUMBER_OF_PAVED_RUNWAYS,NUMBER_OF_UNPAVED_RUNWAYS,LGTH_LONGEST_DAYTIME_RUNWAY,LGTH_LONGEST_NIGHTTIME_RUNWAY,CONTROL_TOWER_IND,INSTRUMENT_FLIGHT_RULES_IND,VISUAL_FLIGHT_RULES_IND,FUEL_AVAILABLE_IND,AIRPORT_LIGHTING,AIRPORT_AREA_HA,COMMENTS,SOURCE_DETAIL,LOCATION_ACCURACY,GEOMETRY_UPDATE_DATETIME,EFFECTIVE_DATETIME,SYSTEM_DATETIME,SE_ANNO_CAD_DATA,OBJECTID",LIO.AMIS_FEATURE_FT,"OGF_ID,AMIS_ID,FEATURE_ID,SITE_NAME,FEATURE_TYPE_DESCR,FEATURE_CLASS_DESCR,HAZARD_STATUS_CODE,HAZARD_STATUS_DESCR,FEAT_DEPTH_HEIGHT,FEAT_WIDTH,FEAT_LENGTH,UTM_ZONE,UTM_EASTING,UTM_NORTHING,LATITUDE_DD,LONGITUDE_DD,FEATURE_CONDITION_DESCR,SYSTEM_DATETIME,OBJECTID,SE_ANNO_CAD_DATA"
    ATTR_ACCUM_MODE = Only Use Result
    COMBINE_GEOM = Use Result
    DATASET = LIO_READ
    FEATURETYPES = LIO.ABORIGINAL_ASSERTION_AREA_FT LIO.ABORIGINAL_ASSERTION_LINE_FT LIO.ABORIGINAL_ASSERTION_POINT_FT LIO.ABORIGINAL_ASSERTION_POLY_FT LIO.ADDITIONAL_NATURAL_AREA_FT LIO.AGG_CATEGORY_14_SITE_FT LIO.AGGSITE_AUTHORIZED_PART_SUR_FT LIO.AGRICULTURAL_LAND_INFO_FT LIO.AIRPORT_OFFICIAL_FT LIO.AIRPORT_OTHER_FT LIO.AMIS_FEATURE_FT
    FORMAT = ORACLE_SPATIAL
    INTERACT = NONE
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = LIO_READ
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = NO
    ORACLE_SPATIAL_USE_SEARCH_ENVELOPE = NO
    ORACLE_SPATIAL_USE_UNIFIED_DATE_ATTRS = YES
    ORDER_RESULTS = No
    OUTPUT_FEATURES_DISPLAY = Schema and Data Features
    WHERE:
      --select table_name
      --from all_tables
      --where table_name like '@Value(REQUESTED_CLASS_LIST)'

      where table_name like 'AIRPORT_OFFICIAL_FT'
FeatureReader
    ATTRIBUTES = LIO.AQUA_OP_PARTNER_HATCHERY_FT,"OGF_ID,AQUACULTURE_LICENCE_NUMBER,OPERATION_NAME,OPERATING_STATUS,FIRST_YEAR_OF_OPERATION,SECURITY_PLAN_IND,CAGE_OPERATION_IND,FLOW_THROUGH_IND,POND_OPERATION_IND,RECIRCULATION_OPERATION_IND,OPERATION_WATER_SOURCE,POINT_SOURCE_DISCHARGE,NUMBER_OF_CAGES,NUMBER_OF_CONTAINERS,NUMBER_OF_PONDS,NUMBER_OF_RACEWAYS,OPERATION_COMMENT,LOCATION_ACCURACY,LOCATION_DESCR,GEOG_UNIT_DESCR,SENSITIVITY_CLASS,SENSITIVITY_DATE,SENSITIVITY_RATIONALE,SENS_RATIONALE_OTHER_DESCR,VERIFICATION_STATUS_FLG,VERIFICATION_STATUS_DATE,BUSINESS_EFF_DATE_FLG,BUSINESS_EFFECTIVE_DATE,BUSINESS_EXPIRY_DATE,SYSTEM_CALCULATED_AREA,SYSTEM_CALCULATED_LENGTH,USER_CALCULATED_METRIC,GENERAL_COMMENTS,GEOMETRY_UPDATE_DATETIME,EFFECTIVE_DATETIME,SYSTEM_DATETIME,OBJECTID,SE_ANNO_CAD_DATA"
    ATTR_ACCUM_MODE = Only Use Result
    COMBINE_GEOM = Use Result
    DATASET = LIO_READ_2
    FEATURETYPES = LIO.AQUA_OP_PARTNER_HATCHERY_FT
    FORMAT = ORACLE_SPATIAL
    INTERACT = NONE
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = LIO_READ_2
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = YES
    ORACLE_SPATIAL_USE_SEARCH_ENVELOPE = NO
    ORACLE_SPATIAL_USE_UNIFIED_DATE_ATTRS = YES
    ORDER_RESULTS = No
    OUTPUT_FEATURES_DISPLAY = Schema and Data Features
AttributeExploder
    ATTR_NAME_LABEL = _attr_name
    ATTR_VALUE_LABEL = _attr_value
    CASE = No
    EXPLODING_TYPE = List
    KEEP_ATTRIBUTES = Yes
    KEEP_GEOMETRY = No
    LIST_NAME = _attr_list
FeatureReader_3
    ATTRS_TO_EXPOSE = fme_feature_type
    ATTR_ACCUM_MODE = Only Use Result
    COMBINE_GEOM = Use Result
    DATASET = LIO_READ_WH
    FEATURETYPES = @Value(TABLE_NAME)
    FORMAT = ORACLE_SPATIAL
    INTERACT = NONE
    MAX_FEATURES = 100
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = LIO_READ_WH
    ORACLE_SPATIAL_ORACLE_SPATIAL_EXPOSE_FORMAT_ATTRS = fme_dataset,char(50) fme_feature_type,char(50) oracle_srid,char(50) oracle_type,char(50)
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = YES
    ORACLE_SPATIAL_USE_SEARCH_ENVELOPE = NO
    ORACLE_SPATIAL_USE_UNIFIED_DATE_ATTRS = YES
    ORDER_RESULTS = No
    OUTPUT_FEATURES_DISPLAY = Schema and Data Features
Creator_3
    GEOMTYPE = Geometry Object
    NUM = 1
    CREATED -> CreateAttrFromUserParam_2
CreateAttrFromUserParam_2: AttributeCreator
    ATTR_TABLE:
      SET_TO REQUESTING_USER (varchar(200)) = $(REQUESTING_USER)
      SET_TO REQUESTED_CLASS_LIST (varchar(200)) = $(REQUESTED_CLASS_LIST)
    -> SQLExecutor_5 [INITIATOR]
Note: should it also query owner or will it always be LIO.
Note: this is prob where join table will need to be (on class_short_name)
SQLExecutor_5
    COMBINE_ATTRS = Result Attributes Only
    COMBINE_GEOM = Initiator Geometry Only
    DATASET = LIO_READ_WH
    EXPOSED_ATTRIBUTE_LIST = TABLE_NAME
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      SELECT table_name
      FROM all_tables
      WHERE owner = 'LIO'
      and table_name = 'TRAPLINE_AREA_STATUS'
      --and table_name = 'TRAPLINE_AREA_FT'
      --and table_name like '%@Value(REQUESTED_CLASS_LIST)%'


      --SELECT table_name
      --FROM all_tables
      --WHERE table_name like '@Value(REQUESTED_CLASS_LIST)'

      --SELECT table_name
      --FROM all_tables
      --WHERE table_name LIKE '%$(REQUESTED_CLASS_LIST)%'


      --SELECT table_name
      --FROM all_tables
      --WHERE table_name = 'LIO.AIRPORT_OFFICIAL_FT'



          --AND table_name LIKE '%$(REQUESTED_CLASS_LIST)%'
       --AND table_name LIKE '%EVAL%' --AIRPORT AIRPTOFF
        --AND table_name LIKE '%' || @Value(REQUESTED_CLASS_LIST) || '%'


      --SELECT table_name
      --FROM all_tables
      --WHERE table_name LIKE '%$(REQUESTED_CLASS_LIST)%'
    RESULT -> SQLExecutor_6 [INITIATOR]
    RESULT -> append_owner_prefix_LIO_2
Note: maybe: need to include OWNER type in the query
SQLExecutor_6
    COMBINE_ATTRS = Result Attributes Only
    COMBINE_GEOM = Initiator Geometry Only
    DATASET = LIO_READ_WH
    EXPOSED_ATTRIBUTE_LIST = OWNER,TABLE_NAME,COLUMN_NAME,DATA_TYPE,COLUMN_ID
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      SELECT OWNER, TABLE_NAME, COLUMN_NAME, DATA_TYPE, COLUMN_ID from all_tab_columns
      where TABLE_NAME = '@Value(TABLE_NAME)'
    RESULT -> AttributeManager_9
AttributeManager_9
    ATTR_TABLE = RENAME_SET_VALUE TABLE_NAME > fme_feature_type (varchar(128))
    -> FeatureWriter_4 [Aggregate]
Note: just rmvd group by
FeatureWriter_4
    DATASET = @Value(fme_feature_type)
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = NO
    FILEGDB_WRITE_UNZONED_UTC = No
    FORMAT = FILEGDB
    TOTAL_FEATURES_WRITTEN_ATTR = _total_features_written
    Aggregate -> CSV00 (writer FILEGDB_6)
CSV00 (writer FILEGDB_6)
    attributes: OWNER text(128), COLUMN_NAME text(128), DATA_TYPE text(128), COLUMN_ID double
append_owner_prefix_LIO_2: AttributeManager
    ATTR_TABLE = SET_TO TABLE_NAME (buffer) = LIO.@Value(TABLE_NAME)
    -> FeatureReader_5 [INITIATOR]
FeatureReader_5
    ATTRS_TO_EXPOSE = fme_feature_type
    ATTR_ACCUM_MODE = Only Use Result
    COMBINE_GEOM = Use Result
    DATASET = LIO_READ_WH
    FEATURETYPES = @Value(TABLE_NAME)
    FORMAT = ORACLE_NONSPATIAL
    ORACLE_NONSPATIAL_CHUNK_SIZE = 200
    ORACLE_NONSPATIAL_CREATE_FEATURE_TABLES_FROM_DATA = Yes
    ORACLE_NONSPATIAL_NAMED_CONNECTION = LIO_READ_WH
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    ORDER_RESULTS = No
    OUTPUT_FEATURES_DISPLAY = Schema and Data Features
    <SCHEMA> -> SchemaScanner_3
    <OTHER> -> AttributeExposer_5
AttributeExposer_5
    ATTR_TABLE = fme_feature_type,
    -> FeatureWriter_7 [Aggregate]
Note: just rmvd group by
FeatureWriter_7
    DATASET = @Value(fme_feature_type)
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = NO
    FILEGDB_WRITE_UNZONED_UTC = No
    FORMAT = FILEGDB
    TOTAL_FEATURES_WRITTEN_ATTR = _total_features_written
    Aggregate -> CSV0000 (writer FILEGDB_6)
CSV0000 (writer FILEGDB_6) [off]
SchemaScanner_3
    CASE = No
    EMPTY_ATTR_HANDLING = IGNORE
    GROUP_BY = fme_feature_type
    HOLD = Yes
    NUMERIC_ALLOW_LEADING_ZEROES = Yes
    SCHEMA_NAME_ATTR = fme_feature_type_name
    UNBOUNDED_NUMBERS = Yes
    UNBOUNDED_STRINGS = No
SQLExecutor_2
    COMBINE_ATTRS = Result Attributes Only
    COMBINE_GEOM = Initiator Geometry Only
    DATASET = LIO_READ_WH
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      select * from "LIO"."TRAPLINE_AREA_FT";
      --select * from LIO.TRAPLINE_AREA_FT;
      --SELECT column_name FROM information_schema.columns
      --WHERE table_name = @Value(TABLE_NAME)
Creator_5
    GEOMTYPE = Geometry Object
    NUM = 1
test_custom_transformer
AttributeExposer_3
    ATTR_TABLE = TABLE_NAME,char(200)
AttributeManager_3
AttributeExploder_8 [off]
    ATTR_NAME_LABEL = _attr_name
    ATTR_VALUE_LABEL = _attr_value
    CASE = No
    EXPLODING_TYPE = Features
    KEEP_ATTRIBUTES = No
    KEEP_GEOMETRY = No
AttributeKeeper_2
    CREATE_BULK_MODE_FEATURES = No
Note: just removed from sql query results
create_column_length: AttributeCreator [off]
    ATTR_TABLE = SET_TO COL_NAME_LEN (varchar(200)) = @StringLength(@Value(COLUMN_NAME))
ListConcatenator
    DROP_EMPTY_PARTS = No
    LIST_ATTR = rows{}.fme_feature_type
    SEP = ,
    VAL_ATTR = _concatenated
AttributeKeeper
    CREATE_BULK_MODE_FEATURES = YES
    KEEP_ATTRS = fme_feature_type
    KEEP_LIST = _list{}.fme_feature_type
    OUTPUT_ON_ATTRIBUTE_CHANGE = fme_feature_type
Creator_2
    GEOMTYPE = Geometry Object
    NUM = 1
    CREATED -> FeatureReader_4 [INITIATOR]
FeatureReader_4
    ATTRS_TO_EXPOSE = fme_feature_type
    ATTR_ACCUM_MODE = Only Use Result
    COMBINE_GEOM = Use Result
    DATASET = $(FME_MF_DIR_ENCODED)Output\LIO.TRAPLINE_AREA_FT.gdb
    FILEGDB_QUERY_FEATURE_TYPES_FOR_MERGE_FILTERS = Yes
    FILEGDB_REMOVE_FEATURE_DATASET = NO
    FILEGDB_SIMPLE_DONUT_GEOMETRY = simple
    FILEGDB_STRIP_GUID_GLOBALID_BRACES = no
    FILEGDB_USE_SEARCH_ENVELOPE = NO
    FORMAT = FILEGDB
    INTERACT = NONE
    ORDER_RESULTS = No
    OUTPUT_FEATURES_DISPLAY = Data Features
poop (writer FILEGDB_5)
CSV (writer FILEGDB_5)
text_line (reader TEXTLINE_3)
    attributes: text_line_data buffer
    -> XMLFlattener
XMLFlattener
    ATTRIBUTE_XML = text_line_data
    EMBEDDED_EXPRESSIONS = @Value(text_line_data)
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = Attribute with XML document
AttributeManager_4
FeatureWriter_3
    DATASET = @Value(fme_feature_type)
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = NO
    FILEGDB_WRITE_UNZONED_UTC = No
    FORMAT = FILEGDB
    GROUP_BY = fme_feature_type
    TOTAL_FEATURES_WRITTEN_ATTR = _total_features_written
AttributeCreator
    ATTR_TABLE = SET_TO fme_feature_type (buffer) = @Value(_list{0}.fme_feature_type)
CSV01 (writer FILEGDB_5)
FeatureWriter_6
    DATASET = @Value(fme_feature_type)
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = NO
    FILEGDB_WRITE_UNZONED_UTC = No
    FORMAT = FILEGDB
    GROUP_BY = fme_feature_type
    TOTAL_FEATURES_WRITTEN_ATTR = _total_features_written
AttributeExploder_4
    ATTR_NAME_LABEL = _attr_name
    ATTR_VALUE_LABEL = _attr_value
    CASE = No
    EXPLODING_TYPE = Features
    KEEP_ATTRIBUTES = No
    KEEP_GEOMETRY = No
FeatureHolder
FeatureClass1 (writer FILEGDB_1)
Note: stub
SchemaScanner_2
    CASE = No
    EMPTY_ATTR_HANDLING = IGNORE
    GROUP_BY = fme_feature_type
    HOLD = Yes
    NUMERIC_ALLOW_LEADING_ZEROES = Yes
    SCHEMA_NAME_ATTR = fme_feature_type_name
    UNBOUNDED_NUMBERS = Yes
    UNBOUNDED_STRINGS = No
Creator_6
    GEOMTYPE = Geometry Object
    NUM = 1
    CREATED -> SQLExecutor_7 [INITIATOR]
Note: maybe: need to include OWNER type in the query
SQLExecutor_7
    COMBINE_ATTRS = Result Attributes Only
    COMBINE_GEOM = Initiator Geometry Only
    DATASET = LIO_READ_WH
    EXPOSED_ATTRIBUTE_LIST = OWNER,TABLE_NAME,COLUMN_NAME,DATA_TYPE,COLUMN_ID
    FORMAT = ORACLE_SPATIAL
    ORACLE_SPATIAL_CREATE_FEATURE_TABLES_FROM_DATA = Yes
    ORACLE_SPATIAL_NAMED_CONNECTION = LIO_READ_WH
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = YES
    ORACLE_SPATIAL_USE_UNIFIED_DATE_ATTRS = YES
    OUTPUT_FEATURES_DISPLAY = Schema and Data Features
    SQL_STATEMENT:
      SELECT OWNER, TABLE_NAME, COLUMN_NAME, DATA_TYPE, COLUMN_ID from all_tab_columns
      where TABLE_NAME = 'TRAPLINE_AREA_FT'
    RESULT -> AttributeCreator_11
AttributeCreator_11
    ATTR_TABLE = SET_TO INDEXER (uint64) = 0
    -> ListBuilder_3
    -> AttributeCreator_14
    -> Counter
AttributeCreator_14
    ATTR_TABLE = SET_TO @Value(COLUMN_NAME) (uint64) = @Value(INDEXER)
    -> AttributeExposer_8
AttributeExposer_8
    ATTR_TABLE = @Value(COLUMN_NAME),buffer
ListBuilder_3
    GROUP_BY = TABLE_NAME INDEXER
    LIST_ATTRS_TO_INCLUDE = COLUMN_ID COLUMN_NAME DATA_TYPE
    LIST_NAME = _list
    -> TestFilter_4
    -> ListSearcher
    -> ListExploder_6
    -> StringSearcher
ListSearcher
    ATTR_VALUE = @Value(_list{@Value(INDEXER)}.COLUMN_NAME)
    CASE = CASE_SENSITIVE
    INDEX_ATTR = _list_index
    LIST_ATTR = _list{}.COLUMN_NAME
    MATCHTYPE = FIRST_MATCHED_ENCODED
    PREFIX = found_
    FOUND -> AttributeCreator_13
AttributeCreator_13
    ATTR_TABLE:
      SET_TO @Value(found_COLUMN_NAME) (uint64) = @Value(INDEXER)
      SET_TO @Value(found_COLUMN_ID) (varchar(200))
    -> AttributeExposer_7
AttributeExposer_7
    ATTR_TABLE = @Value(found_COLUMN_NAME),,SHAPE,
TestFilter_4
    DEFAULT_VALUE = <UNFILTERED>
    PASSED_TEST_GROUP_OUTPUT = FIRST
    TEST_LIST = "BOOL_OP,OR,COMPOSITE_TEST,""""""1"""""",TEST_CLAUSE,TEST _list{@Value(INDEXER)}._element_index ATTRIBUTE_HAS_A_VALUE """,has_value
    has_value -> AttributeCreator_12
AttributeCreator_12
    ATTR_TABLE = SET_TO @Value(_list{@Value(INDEXER)}.COLUMN_NAME) (buffer) = hello
    -> AttributeExposer_4
AttributeExposer_4
    ATTR_TABLE = @Value(_list{@Value(INDEXER)}.COLUMN_NAME),
StringSearcher
    CASE = no
    MATCHED_RESULT_ATTR = _first_match
ListExploder_6
    ATTR_ACCUM_MODE = Merge List Attributes
    ATTR_CONFLICT_RES = Use List Attribute Values
    INDEX_ATTR = _element_index
    LIST_ATTR = _list{}
Counter
    CNT_ATTR = _count
    DOMAIN = counter
    SCOPE = Global
    START = 0
    -> VariableSetter
VariableSetter
    SCOPE = Global
    VALUE = @Value(_count)
    VARNAME = aVariable
    -> ListBuilder_4
ListBuilder_4
    GROUP_BY = TABLE_NAME INDEXER
    LIST_ATTRS_TO_INCLUDE = COLUMN_ID COLUMN_NAME DATA_TYPE _count
    LIST_NAME = _list
    -> TestFilter_5
    -> ListSearcher_3
    -> ListSearcher_2
TestFilter_5
    DEFAULT_VALUE = <UNFILTERED>
    PASSED_TEST_GROUP_OUTPUT = FIRST
    TEST_LIST = "BOOL_OP,OR,COMPOSITE_TEST,""""""1"""""",TEST_CLAUSE,TEST _list{@add(@Value(INDEXER),1,...)}._count ATTRIBUTE_HAS_A_VALUE """,has_value
    has_value -> AttributeManager_10
AttributeManager_10
ListSearcher_2
    ATTR_VALUE = @Value(_list{@Evaluate(@Value(INDEXER)+1)}.COLUMN_NAME)
    CASE = CASE_SENSITIVE
    INDEX_ATTR = _list_index
    LIST_ATTR = _list{}.COLUMN_NAME
    MATCHTYPE = FIRST_MATCHED_ENCODED
    PREFIX = found_
ListSearcher_3
    ATTR_VALUE = @Value(_list{@Value(INDEXER)}.COLUMN_NAME)
    CASE = CASE_SENSITIVE
    INDEX_ATTR = _list_index
    LIST_ATTR = _list{}.COLUMN_NAME
    MATCHTYPE = FIRST_MATCHED_ENCODED
    PREFIX = found_
FeatureJoiner
    ATTR_CONFLICT_RES = Prefer Left
    GEOMETRY_HANDLING = Prefer Left
    GROUP_BY = fme_feature_type_name
    JOIN_KEYS = attribute{0}.name fme_feature_type AUTO
    JOIN_MODE = Full
FeatureReader_8
    ATTRS_TO_EXPOSE = fme_feature_type
    ATTR_ACCUM_MODE = Only Use Result
    COMBINE_GEOM = Use Result
    DATASET = C:\Users\TuAl\OneDrive - Government of Ontario\Documents\GEO-Validator\Test\Output\MNRREG_out\IDKBRUHpt1000.gdb
    FILEGDB_QUERY_FEATURE_TYPES_FOR_MERGE_FILTERS = Yes
    FILEGDB_REMOVE_FEATURE_DATASET = NO
    FILEGDB_SIMPLE_DONUT_GEOMETRY = simple
    FILEGDB_STRIP_GUID_GLOBALID_BRACES = no
    FILEGDB_TABLELIST = @Value(fme_feature_type)
    FILEGDB_USE_SEARCH_ENVELOPE = NO
    FORMAT = FILEGDB
    INTERACT = NONE
    ORDER_RESULTS = No
    OUTPUT_FEATURES_DISPLAY = Schema and Data Features
FeatureMerger
    ATTR_ACCUM_MODE = Merge Supplier
    ATTR_CONFLICT_RES = Use Requestor
    IGNORE_NULLS = No
    MERGE_TYPE = Attributes Only
    PROCESS_DUPS = No
    REJECT_NULL_MISSING_KEYS = No
    SUPPLIERS_FIRST = No
FeatureWriter_8
    DATASET = C:\Users\TuAl\OneDrive - Government of Ontario\Documents\GEO-Validator\Test\Output\MNRREG_out\IDKBRUH.gdb
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = NO
    FILEGDB_WRITE_UNZONED_UTC = No
    FORMAT = FILEGDB
    GROUP_BY = fme_feature_type
    TOTAL_FEATURES_WRITTEN_ATTR = _total_features_written
Creator_7
    GEOMTYPE = Geometry Object
    NUM = 1
    CREATED -> AttributeManager_12
AttributeManager_12
    ATTR_TABLE:
      RENAME_SET_VALUE table_name > table_name_old (uint64) = LIO.TRAPLINE_AREA_FT
      SET_TO table_name (buffer) = LIO.TRAPPER_CABIN_FT
    USER_EXPOSED_ATTRIBUTES = fme_feature_type
    -> FeatureReader_7 [INITIATOR]
FeatureReader_7
    ATTRS_TO_EXPOSE = fme_feature_type
    ATTR_ACCUM_MODE = Only Use Result
    COMBINE_GEOM = Use Result
    DATASET = LIO_READ_WH
    FEATURETYPES = @Value(table_name)
    FORMAT = ORACLE_SPATIAL
    INTERACT = NONE
    MAX_FEATURES = 100
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = LIO_READ_WH
    ORACLE_SPATIAL_ORACLE_SPATIAL_EXPOSE_FORMAT_ATTRS = fme_dataset,char(50) fme_feature_type,char(50) oracle_srid,char(50) oracle_type,char(50)
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = YES
    ORACLE_SPATIAL_USE_SEARCH_ENVELOPE = NO
    ORACLE_SPATIAL_USE_UNIFIED_DATE_ATTRS = YES
    ORDER_RESULTS = No
    OUTPUT_FEATURES_DISPLAY = Schema and Data Features
    <OTHER> -> SchemaScanner_4
Note: need to get actual data types from db / need to see if it works w multiple tables
SchemaScanner_4
    CASE = No
    EMPTY_ATTR_HANDLING = IGNORE
    HOLD = Yes
    NUMERIC_ALLOW_LEADING_ZEROES = Yes
    SCHEMA_NAME_ATTR = fme_feature_type_name
    UNBOUNDED_NUMBERS = Yes
    UNBOUNDED_STRINGS = No
    -> FeatureClass1000100 (writer FILEGDB_8)
    <SCHEMA> -> FeatureClass1000100 (writer FILEGDB_8)
    <SCHEMA> -> FeatureClass100010000 (writer FILEGDB_8)
FeatureClass100010000 (writer FILEGDB_8)
FeatureClass1000100 (writer FILEGDB_8)
Note: just rmvd group by
FeatureWriter_9
    DATASET = C:\Users\TuAl\OneDrive - Government of Ontario\Documents\GEO-Validator\Test\Output\MNRREG_out\IDKBRUHpt1000.gdb
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = NO
    FILEGDB_WRITE_UNZONED_UTC = No
    FORMAT = FILEGDB
    TOTAL_FEATURES_WRITTEN_ATTR = _total_features_written
    Aggregate -> FeatureClass10000 (writer FILEGDB_8)
FeatureClass10000 (writer FILEGDB_8)
AttributeManager_11
    ATTR_TABLE:
      SET_TO INDEXER (uint64) = @add(@Value(INDEXER),1,...)
      SET_TO _list{}._count (int64)
FeatureClass100 (writer FILEGDB_8)
Note: just rmvd group by
FeatureWriter_10
    DATASET = C:\Users\TuAl\OneDrive - Government of Ontario\Documents\GEO-Validator\Test\Output\MNRREG_out\IDKBRUHpt1000.gdb
    DATASET_ATTR = _dataset
    FEATURE_TYPE_LIST_ATTR = _feature_types
    FILEGDB_COORDINATE_SYSTEM_GRANULARITY = FEATURE_TYPE
    FILEGDB_DESTINATION_DATASETTYPE_VALIDATION = Yes
    FILEGDB_ENABLE_LOAD_ONLY_MODE = YES
    FILEGDB_FEATURE_DATASET_HANDLING = WRITE
    FILEGDB_OVERWRITE_GEODB = NO
    FILEGDB_WRITE_UNZONED_UTC = No
    FORMAT = FILEGDB
    TOTAL_FEATURES_WRITTEN_ATTR = _total_features_written
    Aggregate -> FeatureClass10001 (writer FILEGDB_8)
FeatureClass10001 (writer FILEGDB_8)
FeatureClass1 (writer FILEGDB_8)

Bookmark: Rough Drafts - Useless Transformers
AttributeManager [off]
    ATTR_TABLE = SET_TO USER_NAME (varchar(40)) = FME_CONDITIONAL:DEFAULT_VALUE'_FME_NO_OP_'BOOL_OP;OR;COMPOSITE_TEST;1 OR 2;TEST USER_NAME ATTRIBUTE_IS_MISSING _FME_BLANK_STRING_;TEST USER_NAME ATTRIBUTE_VALUE_NULL _FME_BLANK_STRING_'NULL'FME_NUM_CONDITIONS2___
AttributeCreator_3 [off]
    ATTR_TABLE = SET_TO text_line_data (buffer) = LogMessage = 'No match found for user'
AttributeCreator_2 [off]
    ATTR_TABLE = SET_TO text_line_data (buffer) = LogMessage = 'Match found for user: @Value(USER_NAME)'
TestFilter [off]
    DEFAULT_VALUE = Not Found
    PASSED_TEST_GROUP_OUTPUT = FIRST
    TEST_LIST = "BOOL_OP,OR,COMPOSITE_TEST,""""""1"""""",TEST_CLAUSE,TEST @Value(USER_NAME) != 'NULL'",Found
ResultsUserTable: AttributeManager [off]
    ATTR_TABLE:
      REMOVE _created_instance_ (uint64)
      REMOVE _matched_records (uint32)
Temp_FilterLogFromResults: TestFilter [off]
    DEFAULT_VALUE = <UNFILTERED>
    PASSED_TEST_GROUP_OUTPUT = FIRST
    TEST_LIST:
      "BOOL_OP,AND,COMPOSITE_TEST,""""""1 AND 2"""""",TEST_CLAUSE,TEST USER_NAME ATTRIBUTE_HAS_A_VALUE ""
      TEST @Value(_matched_records) != 0",USER_INFO,"BOOL_OP,OR,COMPOSITE_TEST,""""""1"""""",TEST_CLAUSE,TEST @Value(_matched_records) != 0",Log

Bookmark: Verify User Exists In Y_USER_PRIVS Table
Note: Checks for user name with SQL "where" clause. better on memory and speed versus loading it all in then comparing. / _matched_records indicates number of features returned who's user_name matches the requested user's. this attribute is used next in the Tester
FeatureReader_QueryUserPrivsTable
    ATTRIBUTES = LIO.Y_USER_PRIVILEGES,"USER_NAME,CLASS_SHORT_NAME,SUSPENDED,CAN_EDIT,CAN_CHECK_IN,ADMINISTRATOR,FULL_REPLACE,AOR_RESTRICTION,EFFECTIVE_DATETIME"
    ATTR_ACCUM_MODE = Only Use Result
    COMBINE_GEOM = Use Result
    DATASET = LIO_READ_WH
    FEATURETYPES = LIO.Y_USER_PRIVILEGES
    FORMAT = ORACLE_NONSPATIAL
    ORACLE_NONSPATIAL_CHUNK_SIZE = 200
    ORACLE_NONSPATIAL_CREATE_FEATURE_TABLES_FROM_DATA = Yes
    ORACLE_NONSPATIAL_NAMED_CONNECTION = LIO_READ_WH
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    ORDER_RESULTS = No
    OUTPUT_FEATURES_DISPLAY = Schema and Data Features
    WHERE:
      USER_NAME = '@Value(REQUESTING_USER)'
      AND SUSPENDED = 'No' --assuming matt's workspace validates this
      --before getting here but you never know
      AND "CLASS_SHORT_NAME" = '@Value(REQUESTED_CLASS_LIST)'
    LIO.Y_USER_PRIVILEGES -> AttributeManager_CombineOutput
    INITIATOR -> AttributeManager_CombineOutput
AttributeManager_CombineOutput
    ATTR_TABLE:
      REMOVE REQUESTING_USER (varchar(200))
      REMOVE REQUESTED_CLASS_LIST (varchar(200))
      RENAME_SET_VALUE CLASS_SHORT_NAME > REQUESTED_CLASS_LIST (varchar(8))
      REMOVE SUSPENDED (varchar(3))
      REMOVE CAN_EDIT (varchar(3))
      REMOVE CAN_CHECK_IN (varchar(3))
      REMOVE ADMINISTRATOR (varchar(3))
      REMOVE FULL_REPLACE (varchar(3))
      REMOVE AOR_RESTRICTION (varchar(1000))
      REMOVE EFFECTIVE_DATETIME (datetime)
    -> TesterUserFound
TesterUserFound
    BOOL_OP = OR
    TEST_CLAUSE = TEST @Value(_matched_records) != 0
    TEST_MODE = TEST
    PASSED -> CheckMatchedRecords
    FAILED -> AttributeCreator_4

Bookmark: testing_schema_creation
Note: this could be written as the empty schema
ListExploder_2
    ATTR_ACCUM_MODE = Merge List Attributes
    ATTR_CONFLICT_RES = Use List Attribute Values
    INDEX_ATTR = _element_index
    LIST_ATTR = attribute{}
    ELEMENTS -> AttributePivoter
    ELEMENTS -> FeatureTypeFilter
    ELEMENTS -> AttributeCreator_6
    ELEMENTS -> Aggregator_2
    ELEMENTS -> AttributeExploder_5
AttributeCreator_6
    ATTR_TABLE = SET_TO @Value(name) (buffer) = @Value(name)
    -> AttributeRenamer
AttributeRenamer
    ATTR_TABLE = RENAME_SET_DEFAULT temp_value > @Value(name)
    MISSING_INPUT_ATTRS = REMOVE
AttributeExploder_5
    ATTR_NAME_LABEL = _attr_name
    ATTR_VALUE_LABEL = _attr_value
    CASE = No
    EXPLODING_TYPE = Features
    KEEP_ATTRIBUTES = No
    KEEP_GEOMETRY = No
AttributePivoter
    COLUMN_GROUP_ATTR = fme_feature_type_name
    GROUP_TOTALS_TAG = Total
    INCLUDE_GRAND_TOTALS = Yes
    PIVOT_ATTR = fme_feature_type_name
    PIVOT_SUMMARY_TYPES = Count
    ROW_GROUP_ATTRS = fme_feature_type_name
Aggregator_2
    ACCUM_ATTRS_NAME = Drop Incoming Attributes
    AGGREGATE_TYPE = Homogeneous Collection (If Possible)
    GROUP_BY = fme_feature_type_name
    LIST_ATTRS_TO_INCLUDE = fme_data_type name
    LIST_NAME = column_name_data_type
    MODE = Geometry - Assemble One Level
    SEP = ,
FeatureTypeFilter
    ATTRIBUTES = <Blank>,<Unfiltered>
    <BLANK> -> TestFilter_2
TestFilter_2
    DEFAULT_VALUE = <UNFILTERED>
    PASSED_TEST_GROUP_OUTPUT = FIRST
AttributeManager_5
AttributeCreator_7
    ATTR_TABLE = SET_TO text (varchar(200)) = @CurrentAttribute()

Bookmark: NeedToMakeErrorHTML
AttributeCreator_4
    ATTR_TABLE = SET_TO text_line_data (varchar(200)) = LogMessage = 'No match found for user: @Value(REQUESTING_USER)'
    -> text_line (writer TEXTLINE_2)
text_line (writer TEXTLINE_2)
    attributes: text_line_data buffer, text_line_data00 buffer

Bookmark: wtf
SNOW_SURVEY_MEASUREMENT_LOC_FT (reader ORACLE_SPATIAL_2)
    attributes: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
WASTE_MGMT_ATTENUATION_ZONE_FT (reader ORACLE_SPATIAL_2)
    attributes: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
ABORIGINAL_ASSERTION_AREA_FT (reader ORACLE_SPATIAL_2)
    attributes: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
ABORIGINAL_ASSERTION_LINE_FT (reader ORACLE_SPATIAL_2)
    attributes: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
ABORIGINAL_ASSERTION_POINT_FT (reader ORACLE_SPATIAL_2)
    attributes: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
ABORIGINAL_ASSERTION_POLY_FT (reader ORACLE_SPATIAL_2)
    attributes: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
ADDITIONAL_NATURAL_AREA_FT (reader ORACLE_SPATIAL_2)
    attributes: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
AGGSITE_AUTHORIZED_ACTIVE_FT (reader ORACLE_SPATIAL_2)
    attributes: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
AGGSITE_AUTHORIZED_INACTIVE_FT (reader ORACLE_SPATIAL_2)
    attributes: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
AGGSITE_AUTHORIZED_PART_SUR_FT (reader ORACLE_SPATIAL_2)
    attributes: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
AGG_SITE_UNREHABILITATED_FT (reader ORACLE_SPATIAL_2)
    attributes: OGF_ID number(13,0), HAZARD_COMMENT varchar2(2000), GEOMETRY_UPDATE_DATETIME date, EFFECTIVE_DATETIME date, SYSTEM_DATETIME date, OBJECTID number(38,0), SE_ANNO_CAD_DATA blob
AGRICULTURAL_LAND_INFO_FT (reader ORACLE_SPATIAL_2)
    attributes: OGF_ID number(13,0), GIS_ID number(16,0), AGRICULTURAL_USE_TYPE varchar2(10), GEOMETRY_UPDATE_DATETIME date, EFFECTIVE_DATETIME date, SYSTEM_DATETIME date, OBJECTID number(38,0), SE_ANNO_CAD_DATA blob
AQUA_OP_MNR_FISH_CULTURE_FT (reader ORACLE_SPATIAL_2)
    attributes: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
AQUA_OP_PARTNER_HATCHERY_FT (reader ORACLE_SPATIAL_2)
    attributes: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
ARA_WATER_LINE_SEGMENT_FT (reader ORACLE_SPATIAL_2)
    attributes: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
ARA_WATER_LINE_SEGMENT_H_FT (reader ORACLE_SPATIAL_2)
    attributes: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
ARA_WATER_POLY_SEGMENT_H_FT (reader ORACLE_SPATIAL_2)
    attributes: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
BBA_RANDOM_SAMPLE_POINT_FT (reader ORACLE_SPATIAL_2)
    attributes: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
BOREHOLE_GEOCOLUMN_FT (reader ORACLE_SPATIAL_2)
    attributes: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
CANADIAN_HERITAGE_RIVER_FT (reader ORACLE_SPATIAL_2)
    attributes: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
CONS_AUTH_WSHED_AREA_FT (reader ORACLE_SPATIAL_2)
    attributes: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
ENDANGERED_SPECIES_ACT_HAB_FT (reader ORACLE_SPATIAL_2)
    attributes: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
FIRE_MANAGEMENT_ZONE_FT (reader ORACLE_SPATIAL_2)
    attributes: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
FISHERIES_MANAGEMENT_ZONE_FT (reader ORACLE_SPATIAL_2)
    attributes: OGF_ID number(13,0), FISHERIES_MANAGEMENT_ZONE_ID number(2,0), BUSINESS_EFFECTIVE_DATE date, LOCATION_DESCR varchar2(2000), GEOMETRY_UPDATE_DATETIME date, EFFECTIVE_DATETIME date, SYSTEM_DATETIME date, OBJECTID number(38,0), SE_ANNO_CAD_DATA blob
GREENBELT_TOWNS_VILLAGES_FT (reader ORACLE_SPATIAL_2)
    attributes: OGF_ID number(13,0), SETTLEMENT_NAME varchar2(50), SETTLEMENT_NAME_FR varchar2(60), EFFECTIVE_DATETIME date, SYSTEM_DATETIME date, OBJECTID number(38,0), SE_ANNO_CAD_DATA blob
MONITORING_STATION_POINT_FT (reader ORACLE_SPATIAL_2)
    attributes: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
OHN_10M_WATERCOURSE_FT (reader ORACLE_SPATIAL_2)
    attributes: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
ONT_WSHED_BDRY_PRI_DERIVED_FT (reader ORACLE_SPATIAL_2)
    attributes: OGF_ID number(13,0), WATERSHED_NAME varchar2(80), WATERSHED_CODE varchar2(2), AREA_HECTARE number(16,2), SYSTEM_DATETIME date, SE_ANNO_CAD_DATA blob, OBJECTID number(38,0)
ONT_WSHED_BDRY_SEC_DERIVED_FT (reader ORACLE_SPATIAL_2)
    attributes: OGF_ID number(13,0), WATERSHED_NAME varchar2(80), WATERSHED_CODE varchar2(3), AREA_HECTARE number(16,2), SYSTEM_DATETIME date, SE_ANNO_CAD_DATA blob, OBJECTID number(38,0)
PROV_PARK_ZONE_PROPOSED_FT (reader ORACLE_SPATIAL_2)
    attributes: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
SPECIES_MONITORED_SUBJ_TRK_FT (reader ORACLE_SPATIAL_2)
    attributes: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
ARA_WATER_POLY_SEGMENT_FT (reader ORACLE_SPATIAL_2)
    attributes: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
BEAR_MANAGEMENT_AREA_FT (reader ORACLE_SPATIAL_2)
    attributes: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
CARIBOU_RANGE_BOUNDARY_FT (reader ORACLE_SPATIAL_2)
    attributes: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
CL_NON_FREEHOLD_DISPOSITION_FT (reader ORACLE_SPATIAL_2)
    attributes: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
CL_NON_FREEHOLD_DISP_FT_V1 (reader ORACLE_SPATIAL_2)
    attributes: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
CONSERVATION_RESERVE_FT (reader ORACLE_SPATIAL_2)
    attributes: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
CONSULTATION_PROJECT_AREA_FT (reader ORACLE_SPATIAL_2)
    attributes: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
CONSULTATION_PROJECT_LINE_FT (reader ORACLE_SPATIAL_2)
    attributes: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
CONS_AUTH_ADMIN_AREA_FT (reader ORACLE_SPATIAL_2)
    attributes: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
FIRE_RESPONSE_PLAN_AREA_FT (reader ORACLE_SPATIAL_2)
    attributes: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
FISH_SANCTUARY_REGULATED_FT (reader ORACLE_SPATIAL_2)
    attributes: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
GREENBELT_SPECIALTY_CROP_FT (reader ORACLE_SPATIAL_2)
    attributes: OGF_ID number(13,0), CROP_LAND_DESIGNATION varchar2(50), CROP_LAND_DESIGNATION_FR varchar2(90), EFFECTIVE_DATETIME date, SYSTEM_DATETIME date, OBJECTID number(38,0), SE_ANNO_CAD_DATA blob
MUNIC_BND_UPPER_AND_DIST_FT (reader ORACLE_SPATIAL_2)
    attributes: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
NE_MINOR_URBAN_CENTRE_FT (reader ORACLE_SPATIAL_2)
    attributes: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
OHN_HYDROGRAPHIC_POINT_FT (reader ORACLE_SPATIAL_2)
    attributes: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
PETRO_CROWN_LAKE_GRID_FT (reader ORACLE_SPATIAL_2)
    attributes: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
PETRO_DESIG_GAS_STOR_AREA_FT (reader ORACLE_SPATIAL_2)
    attributes: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
RESEARCH_AUXILIARY_POINT_V3 (reader ORACLE_SPATIAL_2)
    attributes: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
SPECIES_OCC_LOC_DERIVED_FT (reader ORACLE_SPATIAL_2)
    attributes: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
WIND_MEASUREMENT_BLOCK_1KM_FT (reader ORACLE_SPATIAL_2)
    attributes: OGF_ID number(13,0), ELEVATION_METRES number(10,0), LOCATION_ACCURACY varchar2(25), BUSINESS_EFFECTIVE_DATE date, GEOMETRY_UPDATE_DATETIME date, EFFECTIVE_DATETIME date, SYSTEM_DATETIME date, OBJECTID number(38,0), SE_ANNO_CAD_DATA blob
CONSULTATION_PROJECT_POINT_FT (reader ORACLE_SPATIAL_2)
    attributes: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
CONSULTATION_PROJECT_POLY_FT (reader ORACLE_SPATIAL_2)
    attributes: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
CROWN_GAME_PRESERVE_FT (reader ORACLE_SPATIAL_2)
    attributes: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
EMERG_MGMT_HISTORICAL_EVENT_FT (reader ORACLE_SPATIAL_2)
    attributes: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
FEDERAL_PROTECTED_AREA_FT (reader ORACLE_SPATIAL_2)
    attributes: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
FIRE_COMMUNICATIONS_TOWER_FT (reader ORACLE_SPATIAL_2)
    attributes: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
FIRE_DISTURBANCE_AREA_FT (reader ORACLE_SPATIAL_2)
    attributes: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
FIRE_DISTURBANCE_POINT_FT (reader ORACLE_SPATIAL_2)
    attributes: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
FIRE_MANAGEMENT_AGREE_AREAFTV2 (reader ORACLE_SPATIAL_2)
    attributes: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
FIRE_MANAGEMENT_AGREE_AREA_FT (reader ORACLE_SPATIAL_2)
    attributes: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
FIRE_MANAGEMENT_AREA_FT (reader ORACLE_SPATIAL_2)
    attributes: OGF_ID number(13,0), OFFICIAL_NAME varchar2(75), BUSINESS_EFFECTIVE_DATE date, GEOMETRY_UPDATE_DATETIME date, EFFECTIVE_DATETIME date, SYSTEM_DATETIME date, OBJECTID number(38,0), SE_ANNO_CAD_DATA blob
FIRST_NATIONS_BOUNDARY_FT (reader ORACLE_SPATIAL_2)
    attributes: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
FISH_HUNT_LIC_ISSUER_LOC_FT (reader ORACLE_SPATIAL_2)
    attributes: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
FISH_PATHOGEN_BOUNDARY_SRC_FT (reader ORACLE_SPATIAL_2)
    attributes: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
FISH_PATHOGEN_MGMT_ZONE_FT (reader ORACLE_SPATIAL_2)
    attributes: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
LANDFORM_CONSERVATION_AREA_FT (reader ORACLE_SPATIAL_2)
    attributes: OGF_ID number(13,0), CLASS_SUBTYPE varchar2(75), CLASS_SUBTYPE_NUM number(7,0), SYSTEM_CALCULATED_AREA number(16,3), GEOMETRY_UPDATE_DATETIME date, EFFECTIVE_DATETIME date, SYSTEM_DATETIME date, OBJECTID number(38,0), SE_ANNO_CAD_DATA blob
MUNIC_BND_LOWER_AND_SINGLE_FT (reader ORACLE_SPATIAL_2)
    attributes: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
OHN_200K_WATERCOURSE_FT (reader ORACLE_SPATIAL_2)
    attributes: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
PATENT_LAND_EXTERNAL_FT (reader ORACLE_SPATIAL_2)
    attributes: OGF_ID number(13,0), PATENT_LAND_ID number(13,0), TITLE_HOLDER_TYPE varchar2(75), CROWN_RESERVATION_TYPE varchar2(40), GEOMETRY_UPDATE_DATETIME date, EFFECTIVE_DATETIME date, SYSTEM_DATETIME date, OBJECTID number(38,0), SE_ANNO_CAD_DATA blob
SPECIES_DATA_CAPTURE_STN_FT (reader ORACLE_SPATIAL_2)
    attributes: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
WILDLIFE_ACTIVITY_AREA_FT (reader ORACLE_SPATIAL_2)
    attributes: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
FISH_SANCTUARY_TEMPORARY_FT (reader ORACLE_SPATIAL_2)
    attributes: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
FOREST_ABIOTIC_DAMAGE_EVENT_FT (reader ORACLE_SPATIAL_2)
    attributes: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
FOREST_DISEASE_DAMAGE_EVENT_FT (reader ORACLE_SPATIAL_2)
    attributes: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
FOREST_INSECT_DAMAGE_EVENT_FT (reader ORACLE_SPATIAL_2)
    attributes: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
FOREST_MANAGEMENT_UNIT_FT (reader ORACLE_SPATIAL_2)
    attributes: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
FOREST_MISC_DAMAGE_EVENT_FT (reader ORACLE_SPATIAL_2)
    attributes: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
FOREST_PROCESSING_FACILITY_FT (reader ORACLE_SPATIAL_2)
    attributes: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
GEOGRAPHIC_LOT_FABRIC_FT (reader ORACLE_SPATIAL_2)
    attributes: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
GEOGRAPHIC_NAMED_EXTENT_FT (reader ORACLE_SPATIAL_2)
    attributes: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
GEOGRAPHIC_TOWNSHIP_IMPR_FT (reader ORACLE_SPATIAL_2)
    attributes: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
GEONAME_FISH_WBYLID_DERIVED_FT (reader ORACLE_SPATIAL_2)
    attributes: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
GEONAME_OPEN_DERIVED_FT (reader ORACLE_SPATIAL_2)
    attributes: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
GREENBELT_DESIGNATION_FT (reader ORACLE_SPATIAL_2)
    attributes: OGF_ID number(13,0), DESIGNATION varchar2(50), DESIGNATION_FR varchar2(50), EFFECTIVE_DATETIME date, SYSTEM_DATETIME date, OBJECTID number(38,0), SE_ANNO_CAD_DATA blob
GREENBELT_OUTER_BOUNDARY_FT (reader ORACLE_SPATIAL_2)
    attributes: OGF_ID number(13,0), EFFECTIVE_DATETIME date, SYSTEM_DATETIME date, SE_ANNO_CAD_DATA blob, OBJECTID number(38,0)
GREENBELT_R_V_CONNECTION_FT (reader ORACLE_SPATIAL_2)
    attributes: OGF_ID number(13,0), EFFECTIVE_DATETIME date, SYSTEM_DATETIME date, SE_ANNO_CAD_DATA blob, OBJECTID number(38,0)
HABITAT_PLANNING_RANGE_FT (reader ORACLE_SPATIAL_2)
    attributes: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
MNRF_ROAD_COND_INSPECT_LN_FT (reader ORACLE_SPATIAL_2)
    attributes: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
MNRF_ROAD_COND_INSPECT_PT_FT (reader ORACLE_SPATIAL_2)
    attributes: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
MNRF_ROAD_X_WATER_BRIDGE_FT (reader ORACLE_SPATIAL_2)
    attributes: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
MNRF_ROAD_X_WAT_NON_BRIDGE_FT (reader ORACLE_SPATIAL_2)
    attributes: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
MOH_SERVICE_LOCATION_FT (reader ORACLE_SPATIAL_2)
    attributes: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
OHN_100K_WATERCOURSE_FT (reader ORACLE_SPATIAL_2)
    attributes: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
ORN_ROAD_NET_ELEMENT_FT (reader ORACLE_SPATIAL_2)
    attributes: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
ORN_SEGMENT_WITH_ADDRESS_FT (reader ORACLE_SPATIAL_2)
    attributes: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
ORWN_STRUCTURE_POINT_FT (reader ORACLE_SPATIAL_2)
    attributes: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
POSTAL_CODE_LOCATION_FT (reader ORACLE_SPATIAL_2)
    attributes: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
PROV_PARK_ADMIN_ZONE_FT (reader ORACLE_SPATIAL_2)
    attributes: OGF_ID number(13,0), ADMIN_ZONE_NAME varchar2(100), GENERAL_COMMENTS varchar2(2000), GEOMETRY_UPDATE_DATETIME date, EFFECTIVE_DATETIME date, SYSTEM_DATETIME date, OBJECTID number(38,0), SE_ANNO_CAD_DATA blob
WILDLIFE_BAITING_OPERATION_FT (reader ORACLE_SPATIAL_2)
    attributes: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
MOOSE_SURVEY_PLOT_GRID_FT (reader ORACLE_SPATIAL_2)
    attributes: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
NATIONAL_WILDLIFE_AREA_FT (reader ORACLE_SPATIAL_2)
    attributes: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
NATURAL_HERITAGE_AREA_FT (reader ORACLE_SPATIAL_2)
    attributes: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
OHN_500K_WATERCOURSE_FT (reader ORACLE_SPATIAL_2)
    attributes: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
OHN_HYDROGRAPHIC_LINE_FT (reader ORACLE_SPATIAL_2)
    attributes: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
OHN_HYDROGRAPHIC_POLY_FT (reader ORACLE_SPATIAL_2)
    attributes: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
OMEIS_MINERAL_INVENTORY_FT (reader ORACLE_SPATIAL_2)
    attributes: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
OMEIS_TECH_FILE_AREA_INT_FT (reader ORACLE_SPATIAL_2)
    attributes: OGF_ID number(13,0), TECH_ID varchar2(20), GEOMETRY_UPDATE_DATETIME date, EFFECTIVE_DATETIME date, SYSTEM_DATETIME date, OBJECTID number(38,0), SE_ANNO_CAD_DATA blob
ONTARIO_DAM_INVENTORY_FT (reader ORACLE_SPATIAL_2)
    attributes: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
ONT_ELEVATION_DATA_INDEX_FT (reader ORACLE_SPATIAL_2)
    attributes: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
ONT_WSHED_BDRY_QUAT_DERIVED_FT (reader ORACLE_SPATIAL_2)
    attributes: OGF_ID number(13,0), WATERSHED_NAME varchar2(80), WATERSHED_CODE varchar2(7), AREA_HECTARE number(16,2), SYSTEM_DATETIME date, SE_ANNO_CAD_DATA blob, OBJECTID number(38,0)
ONT_WSHED_BDRY_TERT_DERIVED_FT (reader ORACLE_SPATIAL_2)
    attributes: OGF_ID number(13,0), WATERSHED_NAME varchar2(80), WATERSHED_CODE varchar2(5), AREA_HECTARE number(16,2), SYSTEM_DATETIME date, SE_ANNO_CAD_DATA blob, OBJECTID number(38,0)
ORM_LAND_USE_DESIGNATION_FT (reader ORACLE_SPATIAL_2)
    attributes: OGF_ID number(13,0), LAND_USE_DESIGNATION varchar2(60), LAND_USE_DESIGNATION_FR varchar2(75), EFFECTIVE_DATETIME date, SYSTEM_DATETIME date, OBJECTID number(38,0), SE_ANNO_CAD_DATA blob
ORM_LAND_USE_DESIGNATION_FT_V3 (reader ORACLE_SPATIAL_2)
    attributes: OGF_ID number(13,0), LAND_USE_DESIGNATION varchar2(60), GEOG_UNIT_DESCR varchar2(2000), GEOMETRY_UPDATE_DATETIME date, EFFECTIVE_DATETIME date, SYSTEM_DATETIME date, OBJECTID number(38,0), SE_ANNO_CAD_DATA blob
PARK_INFRASTRUCTURE_LINE_V3 (reader ORACLE_SPATIAL_2)
    attributes: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
PARK_INFRASTRUCTURE_POINT_V3 (reader ORACLE_SPATIAL_2)
    attributes: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
SOURCE_PROT_AREA_GEN_FT (reader ORACLE_SPATIAL_2)
    attributes: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
PARK_INFRASTRUCTURE_POLYGON_V3 (reader ORACLE_SPATIAL_2)
    attributes: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
PETRO_HISTORICAL_OIL_FIELD_FT (reader ORACLE_SPATIAL_2)
    attributes: OGF_ID number(13,0), HISTORICAL_OIL_FIELD_NAME varchar2(100), GEOMETRY_UPDATE_DATETIME date, EFFECTIVE_DATETIME date, SYSTEM_DATETIME date, OBJECTID number(38,0), SE_ANNO_CAD_DATA blob
PROV_TRK_SPECIES_1KM_GRID_FT (reader ORACLE_SPATIAL_2)
    attributes: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
SIGNIFICANT_ECOLOGICAL_AREA_FT (reader ORACLE_SPATIAL_2)
    attributes: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
SPECIES_OCC_PROV_TRACKED_FT (reader ORACLE_SPATIAL_2)
    attributes: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
TRADITIONAL_LAND_USE_AREA_FT (reader ORACLE_SPATIAL_2)
    attributes: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
WASTE_MANAGEMENT_SITE_FT (reader ORACLE_SPATIAL_2)
    attributes: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
WILDLAND_FIRE_OPPORTUNITY_FT (reader ORACLE_SPATIAL_2)
    attributes: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
WPOWER_GENERATION_STATION_FT (reader ORACLE_SPATIAL_2)
    attributes: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
WPOWER_POTENTIAL_SITE_FT (reader ORACLE_SPATIAL_2)
    attributes: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
AGG_CATEGORY_14_SITE_FT (reader ORACLE_SPATIAL_2)
    attributes: OGF_ID number(13,0), FOREST_ROAD_AGG_OPERATOR varchar2(200), START_OF_OPERATION_DATE date, GEOMETRY_UPDATE_DATETIME date, EFFECTIVE_DATETIME date, SYSTEM_DATETIME date, OBJECTID number(38,0), SE_ANNO_CAD_DATA blob
AGG_DESIGNATED_AREA_FT (reader ORACLE_SPATIAL_2)
    attributes: OGF_ID number(13,0), GEOMETRY_UPDATE_DATETIME date, EFFECTIVE_DATETIME date, SYSTEM_DATETIME date, OBJECTID number(38,0), SE_ANNO_CAD_DATA blob
AGG_EXTRACTION_AREA_FT (reader ORACLE_SPATIAL_2)
    attributes: OGF_ID number(13,0), EXTRACTION_TYPE varchar2(10), AGG_SITE_AUTHORIZED_ID number(13,0), GEOMETRY_UPDATE_DATETIME date, EFFECTIVE_DATETIME date, SYSTEM_DATETIME date, OBJECTID number(38,0), SE_ANNO_CAD_DATA blob
AGG_INSPECTOR_JURIS_FT (reader ORACLE_SPATIAL_2)
    attributes: OGF_ID number(13,0), OFFICIAL_NAME varchar2(100), ADMIN_NUMBER number(5,0), AGGREGATE_OFFICER varchar2(100), GEOMETRY_UPDATE_DATETIME date, EFFECTIVE_DATETIME date, SYSTEM_DATETIME date, OBJECTID number(38,0), SE_ANNO_CAD_DATA blob
AGG_SITE_AUTHORIZED_FT (reader ORACLE_SPATIAL_2)
    attributes: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
AIRPORT_OFFICIAL_FT (reader ORACLE_SPATIAL_2)
    attributes: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
AIRPORT_OTHER_FT (reader ORACLE_SPATIAL_2)
    attributes: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
AMIS_FEATURE_FT (reader ORACLE_SPATIAL_2)
    attributes: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
AQUA_AREA_OF_IMPACT_FT (reader ORACLE_SPATIAL_2)
    attributes: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
AQUA_OP_PRIVATE_FT (reader ORACLE_SPATIAL_2)
    attributes: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
ASSESSMENT_PARCEL_FT (reader ORACLE_SPATIAL_2)
    attributes: OGF_ID number(13,0), ASSESSMENT_ROLL_NUMBER varchar2(20), GEOMETRY_UPDATE_DATETIME date, EFFECTIVE_DATETIME date, SYSTEM_DATETIME date, OBJECTID number(38,0), SE_ANNO_CAD_DATA blob
BAIT_RETAIL_LOCATION_FT (reader ORACLE_SPATIAL_2)
    attributes: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
ELC_COMMUNITY_AREA_FT (reader ORACLE_SPATIAL_2)
    attributes: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
FIRE_WEATHER_STATION_FT (reader ORACLE_SPATIAL_2)
    attributes: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
INDIAN_RESERVE_FT (reader ORACLE_SPATIAL_2)
    attributes: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
MDI_MINERAL_DEPOSIT_FT (reader ORACLE_SPATIAL_2)
    attributes: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
ORWN_JUNCTION_FT (reader ORACLE_SPATIAL_2)
    attributes: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
OWNERSHIP_PARCEL_FT (reader ORACLE_SPATIAL_2)
    attributes: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
ARA_SURVEY_POINT_FT (reader ORACLE_SPATIAL_2)
    attributes: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
BAIT_HARVEST_AREA_FT (reader ORACLE_SPATIAL_2)
    attributes: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
BATHYMETRY_INDEX_FT (reader ORACLE_SPATIAL_2)
    attributes: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
BATHYMETRY_LINE_FT (reader ORACLE_SPATIAL_2)
    attributes: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
BATHYMETRY_POINT_FT (reader ORACLE_SPATIAL_2)
    attributes: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
BOAT_CACHE_LOCATION_FT (reader ORACLE_SPATIAL_2)
    attributes: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
BROADBAND_AREA_FT (reader ORACLE_SPATIAL_2)
    attributes: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
BUILDING_AS_SYMBOL_FT (reader ORACLE_SPATIAL_2)
    attributes: OBJECTID number(38,0), OGF_ID number(13,0), BUILDING_TYPE varchar2(30), ROTATION number(3,0), LOCATION_ACCURACY varchar2(25), GEOMETRY_UPDATE_DATETIME date, EFFECTIVE_DATETIME date, SYSTEM_DATETIME date, SE_ANNO_CAD_DATA blob
BUILDING_TO_SCALE_FT (reader ORACLE_SPATIAL_2)
    attributes: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
BUILT_UP_AREA_FT (reader ORACLE_SPATIAL_2)
    attributes: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
CADASTRAL_LOCATION_FT (reader ORACLE_SPATIAL_2)
    attributes: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
CLUPA_OVERLAY_FT (reader ORACLE_SPATIAL_2)
    attributes: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
CLUPA_PROVINCIAL_FT (reader ORACLE_SPATIAL_2)
    attributes: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
CL_PATENT_LAND_FT (reader ORACLE_SPATIAL_2)
    attributes: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
CL_TENURE_PENDING_FT (reader ORACLE_SPATIAL_2)
    attributes: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
CL_UNPATENTED_FT (reader ORACLE_SPATIAL_2)
    attributes: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
CONSTRUCTED_DRAIN_FT (reader ORACLE_SPATIAL_2)
    attributes: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
LAND_USE_PLAN_AREA_FT (reader ORACLE_SPATIAL_2)
    attributes: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
MNR_DISTRICT_FT (reader ORACLE_SPATIAL_2)
    attributes: OGF_ID number(13,0), DISTRICT_NAME varchar2(75), REGION_NAME varchar2(75), GEOMETRY_UPDATE_DATETIME date, EFFECTIVE_DATETIME date, SYSTEM_DATETIME date, SE_ANNO_CAD_DATA blob, OBJECTID number(38,0)
MNR_ROAD_BARRIER_FT (reader ORACLE_SPATIAL_2)
    attributes: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
MOH_LHIN_BOUNDARY_FT (reader ORACLE_SPATIAL_2)
    attributes: OGF_ID number(13,0), LHIN_IDENT varchar2(2), LHIN_NAME_ENG varchar2(50), LHIN_NAME_FR varchar2(50), GEOMETRY_UPDATE_DATETIME date, EFFECTIVE_DATETIME date, SYSTEM_DATETIME date, OBJECTID number(38,0), SE_ANNO_CAD_DATA blob
MUNICIPAL_UPPER_TIER_FT (reader ORACLE_SPATIAL_2)
    attributes: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
NE_POLICY_AREA_FT (reader ORACLE_SPATIAL_2)
    attributes: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
OHN_1M_WATERBODY_FT (reader ORACLE_SPATIAL_2)
    attributes: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
OHN_2M_WATERCOURSE_FT (reader ORACLE_SPATIAL_2)
    attributes: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
OHN_WATERCOURSE_FT (reader ORACLE_SPATIAL_2)
    attributes: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
ORWN_CROSSING_FT (reader ORACLE_SPATIAL_2)
    attributes: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
PATENT_LAND_FT (reader ORACLE_SPATIAL_2)
    attributes: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
CONTAMINATED_SITE_FT (reader ORACLE_SPATIAL_2)
    attributes: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
COSINE_STATION_FT (reader ORACLE_SPATIAL_2)
    attributes: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
CROWN_PARCEL_FT (reader ORACLE_SPATIAL_2)
    attributes: OGF_ID number(13,0), CROWN_PARCEL_IDENTIFIER varchar2(13), GEOMETRY_UPDATE_DATETIME date, EFFECTIVE_DATETIME date, SYSTEM_DATETIME date, OBJECTID number(38,0), SE_ANNO_CAD_DATA blob
DRAIN_CONNECTION_FT (reader ORACLE_SPATIAL_2)
    attributes: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
FEDERAL_LAND_OTHER_FT (reader ORACLE_SPATIAL_2)
    attributes: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
FEDERAL_RIDING_FT (reader ORACLE_SPATIAL_2)
    attributes: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
FIRE_FACILITY_POINT_FT (reader ORACLE_SPATIAL_2)
    attributes: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
FIRE_FUEL_CACHE_FT (reader ORACLE_SPATIAL_2)
    attributes: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
FIRE_RESPONSE_SECTOR_FT (reader ORACLE_SPATIAL_2)
    attributes: OGF_ID number(13,0), RESPONSE_SECTOR varchar2(3), BASE_RESPONSIBLE varchar2(3), GEOMETRY_UPDATE_DATETIME date, EFFECTIVE_DATETIME date, SYSTEM_DATETIME date, OBJECTID number(38,0), SE_ANNO_CAD_DATA blob
FIRE_WEATHER_SECTOR_FT (reader ORACLE_SPATIAL_2)
    attributes: OGF_ID number(13,0), OFFICIAL_NAME varchar2(75), FIRE_WEATHER_SECTOR_CODE varchar2(5), BUSINESS_EFFECTIVE_DATE date, GEOMETRY_UPDATE_DATETIME date, EFFECTIVE_DATETIME date, SYSTEM_DATETIME date, OBJECTID number(38,0), SE_ANNO_CAD_DATA blob
FISHING_ACCESS_POINT_FT (reader ORACLE_SPATIAL_2)
    attributes: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
FISH_ACTIVITY_AREA_FT (reader ORACLE_SPATIAL_2)
    attributes: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
FOREST_COVER_UNIT_FT (reader ORACLE_SPATIAL_2)
    attributes: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
MUNICIPAL_PARK_FT (reader ORACLE_SPATIAL_2)
    attributes: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
MUNICIPAL_WARD_FT (reader ORACLE_SPATIAL_2)
    attributes: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
OHN_1M_SHORELINE_FT (reader ORACLE_SPATIAL_2)
    attributes: OGF_ID number(13,0), POLITICAL_SUBDIVISION_CODE varchar2(5), GEOMETRY_UPDATE_DATETIME date, EFFECTIVE_DATETIME date, SYSTEM_DATETIME date, OBJECTID number(38,0), SE_ANNO_CAD_DATA blob
OHN_1M_WATERCOURSE_FT (reader ORACLE_SPATIAL_2)
    attributes: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
OHN_200K_WATERBODY_FT (reader ORACLE_SPATIAL_2)
    attributes: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
OHN_500K_SHORELINE_FT (reader ORACLE_SPATIAL_2)
    attributes: OGF_ID number(13,0), POLITICAL_SUBDIVISION_CODE varchar2(5), GEOMETRY_UPDATE_DATETIME date, EFFECTIVE_DATETIME date, SYSTEM_DATETIME date, OBJECTID number(38,0), SE_ANNO_CAD_DATA blob
ONT_WSHED_BDRY_FT (reader ORACLE_SPATIAL_2)
    attributes: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
OTN_ACCESS_POINT_FT (reader ORACLE_SPATIAL_2)
    attributes: OGF_ID number(13,0), LOCATION_ACCURACY varchar2(25), GEOMETRY_UPDATE_DATETIME date, EFFECTIVE_DATETIME date, SYSTEM_DATETIME date, OBJECTID number(38,0), SE_ANNO_CAD_DATA blob
OTN_SEGMENT_DERIVED_FT (reader ORACLE_SPATIAL_2)
    attributes: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
RE_APPLICATION_AREA_FT (reader ORACLE_SPATIAL_2)
    attributes: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
FOREST_GENETICS_SITE_FT (reader ORACLE_SPATIAL_2)
    attributes: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
FOREST_GENETICS_ZONE_FT (reader ORACLE_SPATIAL_2)
    attributes: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
FRI_WETLAND_FT (reader ORACLE_SPATIAL_2)
    attributes: OGF_ID number(13,0), CLASS_SUBTYPE varchar2(75), CLASS_SUBTYPE_NUM number(7,0), SYSTEM_CALC_METRIC number(16,3), GEOMETRY_UPDATE_DATETIME date, EFFECTIVE_DATETIME date, SYSTEM_DATETIME date, OBJECTID number(38,0), SE_ANNO_CAD_DATA blob
GREENBELT_HAMLET_FT (reader ORACLE_SPATIAL_2)
    attributes: OGF_ID number(13,0), HAMLET_NAME varchar2(50), HAMLET_NAME_FR varchar2(60), EFFECTIVE_DATETIME date, SYSTEM_DATETIME date, OBJECTID number(38,0), SE_ANNO_CAD_DATA blob
LAKE_SIMCOE_PAWB_FT (reader ORACLE_SPATIAL_2)
    attributes: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
LAT_LONG_LINE_FT (reader ORACLE_SPATIAL_2)
    attributes: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
MAI_PLOT_GRID_FT (reader ORACLE_SPATIAL_2)
    attributes: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
MINING_CLAIM_FT (reader ORACLE_SPATIAL_2)
    attributes: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
MNRF_ROAD_SEGMENT_FT (reader ORACLE_SPATIAL_2)
    attributes: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
MNRF_ROAD_X_RAILWAY_FT (reader ORACLE_SPATIAL_2)
    attributes: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
MNR_ROAD_BARRIER_FT_5 (reader ORACLE_SPATIAL_2)
    attributes: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
MNR_SIGN_SITE_FT (reader ORACLE_SPATIAL_2)
    attributes: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
MOH_PHU_BOUNDARY_FT (reader ORACLE_SPATIAL_2)
    attributes: OGF_ID number(13,0), PHU_ID number(4,0), PHU_NAME_ENG varchar2(75), PHU_NAME_FR varchar2(75), GEOMETRY_UPDATE_DATETIME date, EFFECTIVE_DATETIME date, SYSTEM_DATETIME date, OBJECTID number(38,0), SE_ANNO_CAD_DATA blob
MONITORING_STATION_FT (reader ORACLE_SPATIAL_2)
    attributes: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
OHN_100K_SHORELINE_FT (reader ORACLE_SPATIAL_2)
    attributes: OGF_ID number(13,0), POLITICAL_SUBDIVISION_CODE varchar2(5), GEOMETRY_UPDATE_DATETIME date, EFFECTIVE_DATETIME date, SYSTEM_DATETIME date, OBJECTID number(38,0), SE_ANNO_CAD_DATA blob
OTN_SEGMENT_FT (reader ORACLE_SPATIAL_2)
    attributes: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
MUNICIPAL_LOWER_TIER_FT (reader ORACLE_SPATIAL_2)
    attributes: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
NEPOSS_PARK_FT (reader ORACLE_SPATIAL_2)
    attributes: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
NE_PLAN_BOUNDARY_FT (reader ORACLE_SPATIAL_2)
    attributes: OGF_ID number(13,0), LOCATION_ACCURACY varchar2(25), GEOMETRY_UPDATE_DATETIME date, EFFECTIVE_DATETIME date, SYSTEM_DATETIME date, SE_ANNO_CAD_DATA blob, OBJECTID number(38,0)
NE_PLAN_DESIGNATION_FT (reader ORACLE_SPATIAL_2)
    attributes: OGF_ID number(13,0), DESIGNATION varchar2(35), LOCATION_ACCURACY varchar2(25), GEOMETRY_UPDATE_DATETIME date, EFFECTIVE_DATETIME date, SYSTEM_DATETIME date, SE_ANNO_CAD_DATA blob, OBJECTID number(38,0)
NTS_250_GRID_FT (reader ORACLE_SPATIAL_2)
    attributes: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
OHN_100K_WATERBODY_FT (reader ORACLE_SPATIAL_2)
    attributes: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
OHN_10M_SHORELINE_FT (reader ORACLE_SPATIAL_2)
    attributes: OGF_ID number(13,0), POLITICAL_SUBDIVISION_CODE varchar2(5), GEOMETRY_UPDATE_DATETIME date, EFFECTIVE_DATETIME date, SYSTEM_DATETIME date, OBJECTID number(38,0), SE_ANNO_CAD_DATA blob
OHN_10M_WATERBODY_FT (reader ORACLE_SPATIAL_2)
    attributes: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
OHN_200K_SHORELINE_FT (reader ORACLE_SPATIAL_2)
    attributes: OGF_ID number(13,0), POLITICAL_SUBDIVISION_CODE varchar2(5), GEOMETRY_UPDATE_DATETIME date, EFFECTIVE_DATETIME date, SYSTEM_DATETIME date, OBJECTID number(38,0), SE_ANNO_CAD_DATA blob
OHN_2M_SHORELINE_FT (reader ORACLE_SPATIAL_2)
    attributes: OGF_ID number(13,0), POLITICAL_SUBDIVISION_CODE varchar2(5), GEOMETRY_UPDATE_DATETIME date, EFFECTIVE_DATETIME date, SYSTEM_DATETIME date, OBJECTID number(38,0), SE_ANNO_CAD_DATA blob
OHN_2M_WATERBODY_FT (reader ORACLE_SPATIAL_2)
    attributes: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
OHN_500K_WATERBODY_FT (reader ORACLE_SPATIAL_2)
    attributes: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
OHN_5M_SHORELINE_FT (reader ORACLE_SPATIAL_2)
    attributes: OGF_ID number(13,0), POLITICAL_SUBDIVISION_CODE varchar2(5), GEOMETRY_UPDATE_DATETIME date, EFFECTIVE_DATETIME date, SYSTEM_DATETIME date, OBJECTID number(38,0), SE_ANNO_CAD_DATA blob
OHN_5M_WATERBODY_FT (reader ORACLE_SPATIAL_2)
    attributes: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
OHN_5M_WATERCOURSE_FT (reader ORACLE_SPATIAL_2)
    attributes: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
OHN_SHORELINE_FT (reader ORACLE_SPATIAL_2)
    attributes: OGF_ID number(13,0), EFFECTIVE_DATETIME date, OBJECTID number(38,0), SE_ANNO_CAD_DATA blob, SYSTEM_DATETIME date
OHN_WATERBODY_FT (reader ORACLE_SPATIAL_2)
    attributes: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
OMEIS_DRILL_HOLE_FT (reader ORACLE_SPATIAL_2)
    attributes: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
OMEIS_TECH_FILE_AREA_FT (reader ORACLE_SPATIAL_2)
    attributes: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
ORM_PLANNING_AREA_FT (reader ORACLE_SPATIAL_2)
    attributes: OGF_ID number(13,0), EFFECTIVE_DATETIME date, SYSTEM_DATETIME date, OBJECTID number(38,0), SE_ANNO_CAD_DATA blob
ORWN_MARKER_POST_FT (reader ORACLE_SPATIAL_2)
    attributes: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
ORWN_STATION_FT (reader ORACLE_SPATIAL_2)
    attributes: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
ORWN_STRUCTURE_LINE_FT (reader ORACLE_SPATIAL_2)
    attributes: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
ORWN_TRACK_FT (reader ORACLE_SPATIAL_2)
    attributes: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
PC_OBSERVATION_FT (reader ORACLE_SPATIAL_2)
    attributes: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
PC_OCCURRENCE_FT (reader ORACLE_SPATIAL_2)
    attributes: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
PETROLEUM_WELL_FT (reader ORACLE_SPATIAL_2)
    attributes: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
RESEARCH_LINE_V3 (reader ORACLE_SPATIAL_2)
    attributes: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
SOIL_SURVEY_COMPLEX_FT (reader ORACLE_SPATIAL_2)
    attributes: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
TRAPPER_CABIN_FT (reader ORACLE_SPATIAL_2)
    attributes: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
PROV_PARK_REGULATED_FT (reader ORACLE_SPATIAL_2)
    attributes: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
PROV_PARK_ZONE_FT (reader ORACLE_SPATIAL_2)
    attributes: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
PWQMN_STATION_FT (reader ORACLE_SPATIAL_2)
    attributes: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
RESEARCH_POINT_V3 (reader ORACLE_SPATIAL_2)
    attributes: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
RESEARCH_POLYGON_V3 (reader ORACLE_SPATIAL_2)
    attributes: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
RESTRICTED_FIRE_ZONE_FT (reader ORACLE_SPATIAL_2)
    attributes: OGF_ID number(13,0), OFFICIAL_NAME varchar2(75), BUSINESS_EFFECTIVE_DATE date, GEOMETRY_UPDATE_DATETIME date, EFFECTIVE_DATETIME date, SYSTEM_DATETIME date, OBJECTID number(38,0), SE_ANNO_CAD_DATA blob
SETTLEMENT_100K_FT (reader ORACLE_SPATIAL_2)
    attributes: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
SPECIES_OBSERVATION_FT (reader ORACLE_SPATIAL_2)
    attributes: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
SPECIES_OBS_PROV_FT (reader ORACLE_SPATIAL_2)
    attributes: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
SPECIES_SEARCH_AREA_FT (reader ORACLE_SPATIAL_2)
    attributes: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
TILE_DRAINAGE_AREA_FT (reader ORACLE_SPATIAL_2)
    attributes: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
TRAIL_SEGMENT_FT (reader ORACLE_SPATIAL_2)
    attributes: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
TRAPLINE_AREA_FT (reader ORACLE_SPATIAL_2)
    attributes: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
UNORGANIZED_AREA_FT (reader ORACLE_SPATIAL_2)
    attributes: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
UTM_100KM_GRID_FT (reader ORACLE_SPATIAL_2)
    attributes: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
UTM_10KM_GRID_FT (reader ORACLE_SPATIAL_2)
    attributes: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
UTM_1KM_GRID_FT (reader ORACLE_SPATIAL_2)
    attributes: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
UTM_5KM_GRID_FT (reader ORACLE_SPATIAL_2)
    attributes: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
WASTE_DISPOSAL_SITE_FT (reader ORACLE_SPATIAL_2)
    attributes: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
WATER_SUPPLY_FT (reader ORACLE_SPATIAL_2)
    attributes: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
WCA_OBSERVATION_FT (reader ORACLE_SPATIAL_2)
    attributes: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
WCA_OCCURRENCE_FT (reader ORACLE_SPATIAL_2)
    attributes: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
WILDERNESS_AREA_FT (reader ORACLE_SPATIAL_2)
    attributes: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
WILDLIFE_ACTIVITY_SITE_FT (reader ORACLE_SPATIAL_2)
    attributes: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
WILDLIFE_MGMT_AREA_FT (reader ORACLE_SPATIAL_2)
    attributes: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
WILDLIFE_MGMT_UNIT_FT (reader ORACLE_SPATIAL_2)
    attributes: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
WILD_RICE_STAND_FT (reader ORACLE_SPATIAL_2)
    attributes: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
WIND_TURBINE_FT (reader ORACLE_SPATIAL_2)
    attributes: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
WOODED_AREA_FT (reader ORACLE_SPATIAL_2)
    attributes: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
AMIS_SITE_FT (reader ORACLE_SPATIAL_2)
    attributes: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
ANSI_FT (reader ORACLE_SPATIAL_2)
    attributes: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
PROVINCE_FT (reader ORACLE_SPATIAL_2)
    attributes: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
ORN_CLIP_FT (reader ORACLE_SPATIAL_2)
    attributes: OGF_ID number(13,0), OFFICIAL_NAME varchar2(75), GEOMETRY_UPDATE_DATETIME date, EFFECTIVE_DATETIME date, SYSTEM_DATETIME date, SE_ANNO_CAD_DATA blob, OBJECTID number(38,0)
PETRO_POOL_FT (reader ORACLE_SPATIAL_2)
    attributes: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
CONTOUR_FT (reader ORACLE_SPATIAL_2)
    attributes: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
ECODISTRICT_FT (reader ORACLE_SPATIAL_2)
    attributes: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
ECOREGION_FT (reader ORACLE_SPATIAL_2)
    attributes: OGF_ID number(13,0), ECOREGION_NAME varchar2(75), ECOREGION_CODE varchar2(2), ECOZONE_NAME varchar2(75), GEOMETRY_UPDATE_DATETIME date, EFFECTIVE_DATETIME date, SYSTEM_DATETIME date, SE_ANNO_CAD_DATA blob, OBJECTID number(38,0)
ECOZONE_FT (reader ORACLE_SPATIAL_2)
    attributes: OGF_ID number(13,0), ECOZONE_NAME varchar2(75), GEOMETRY_UPDATE_DATETIME date, EFFECTIVE_DATETIME date, SYSTEM_DATETIME date, SE_ANNO_CAD_DATA blob, OBJECTID number(38,0)
NTS_50_GRID_FT (reader ORACLE_SPATIAL_2)
    attributes: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
TOWER_FT (reader ORACLE_SPATIAL_2)
    attributes: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
FRI_STATUS_FT (reader ORACLE_SPATIAL_2)
    attributes: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
MINE_SITE_FT (reader ORACLE_SPATIAL_2)
    attributes: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
MNR_AREA_FT (reader ORACLE_SPATIAL_2)
    attributes: OGF_ID number(13,0), AREA_NAME varchar2(75), DISTRICT_NAME varchar2(75), REGION_NAME varchar2(75), GEOMETRY_UPDATE_DATETIME date, EFFECTIVE_DATETIME date, SYSTEM_DATETIME date, SE_ANNO_CAD_DATA blob, OBJECTID number(38,0)
MNR_REGION_FT (reader ORACLE_SPATIAL_2)
    attributes: OGF_ID number(13,0), REGION_NAME varchar2(75), GEOMETRY_UPDATE_DATETIME date, EFFECTIVE_DATETIME date, SYSTEM_DATETIME date, SE_ANNO_CAD_DATA blob, OBJECTID number(38,0)
OPS_REGION_FT (reader ORACLE_SPATIAL_2)
    attributes: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
WETLAND_FT (reader ORACLE_SPATIAL_2)
    attributes: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
MTO_CLIP_FT (reader ORACLE_SPATIAL_2)
    attributes: OGF_ID number(13,0), OFFICIAL_NAME varchar2(75), GEOMETRY_UPDATE_DATETIME date, EFFECTIVE_DATETIME date, SYSTEM_DATETIME date, SE_ANNO_CAD_DATA blob, OBJECTID number(38,0)
NHS_AREA_FT (reader ORACLE_SPATIAL_2)
    attributes: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
SITE_DISTRICT_FT (reader ORACLE_SPATIAL_2)
    attributes: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
SITE_REGION_FT (reader ORACLE_SPATIAL_2)
    attributes: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
SPOT_HEIGHT_FT (reader ORACLE_SPATIAL_2)
    attributes: OGF_ID number(13,0), ELEVATION number(10,1), SPOT_HEIGHT_TYPE varchar2(40), GEOMETRY_UPDATE_DATETIME date, EFFECTIVE_DATETIME date, SYSTEM_DATETIME date, OBJECTID number(38,0), SE_ANNO_CAD_DATA blob
UTILITY_LINE_FT (reader ORACLE_SPATIAL_2)
    attributes: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
UTILITY_SITE_FT (reader ORACLE_SPATIAL_2)
    attributes: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

Bookmark: from xml reader
CodedValues (reader XML_1)
    attributes: xml_fragment xml_xml, xml_id xml_char(25), xml_matched_element xml_char(11), xml_parent_child_pos xml_decimal(1,0), xml_parent_id xml_char(18)
Description (reader XML_1)
    attributes: xml_fragment xml_xml, xml_id xml_char(25), xml_matched_element xml_char(11), xml_parent_child_pos xml_decimal(1,0), xml_parent_id xml_char(18)
Domain (reader XML_1)
    attributes: xml_fragment xml_xml, xml_id xml_char(18), xml_matched_element xml_char(6), xml_parent_child_pos xml_char(1), xml_parent_id xml_char(1)
DomainName (reader XML_1)
    attributes: xml_fragment xml_xml, xml_id xml_char(24), xml_matched_element xml_char(10), xml_parent_child_pos xml_decimal(1,0), xml_parent_id xml_char(18)
FieldType (reader XML_1)
    attributes: xml_fragment xml_xml, xml_id xml_char(23), xml_matched_element xml_char(9), xml_parent_child_pos xml_decimal(1,0), xml_parent_id xml_char(18)
MergePolicy (reader XML_1)
    attributes: xml_fragment xml_xml, xml_id xml_char(25), xml_matched_element xml_char(11), xml_parent_child_pos xml_decimal(1,0), xml_parent_id xml_char(18)
Owner (reader XML_1)
    attributes: xml_fragment xml_xml, xml_id xml_char(19), xml_matched_element xml_char(5), xml_parent_child_pos xml_decimal(1,0), xml_parent_id xml_char(18)
SplitPolicy (reader XML_1)
    attributes: xml_fragment xml_xml, xml_id xml_char(25), xml_matched_element xml_char(11), xml_parent_child_pos xml_decimal(1,0), xml_parent_id xml_char(18)

Bookmark: Non-Functional
Note: disabled

Bookmark: Questions
Note: How to make user param selecting the requested_class_list, use the lio table names (i tried to import, gets the attributes of the tables not just the table/name of table)
Note: When verifying user params, what params should we look for to figure out if they can access the lio db. is there a specific table they can and cannot see? which we would have to verify against the requested_class_list

FME custom transformer test_custom_transformer
testing how to separate features

FmeFeatureType_Input (input)
    -> FeatureTypeFilter
FeatureTypeFilter
    ATTRIBUTES = <Blank>,<Unfiltered>
AttributeFilter
    ATTR_VALUES = <Empty>,<Missing>,<Null>,<Unfiltered>
Output (output)
